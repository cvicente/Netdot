-- *****************************************************************
-- CISCO-SERVICE-CONTROLLER-MIB.my
--   
-- MIB file for Service Controller.
-- Apr 2009, Or Dubnov-Raz
--   
-- Copyright (c) 2007-2009 by Cisco Systems Inc.
-- All rights reserved.
--   
-- ***************************************************************

CISCO-SERVICE-CONTROLLER-MIB DEFINITIONS ::= BEGIN

IMPORTS
    MODULE-IDENTITY,
    OBJECT-TYPE,
    Unsigned32
        FROM SNMPv2-SMI
    MODULE-COMPLIANCE,
    OBJECT-GROUP
        FROM SNMPv2-CONF
    entPhysicalIndex
        FROM ENTITY-MIB
    SnmpAdminString
        FROM SNMP-FRAMEWORK-MIB
    ciscoMgmt
        FROM CISCO-SMI;


ciscoServiceControllerMIB MODULE-IDENTITY
    LAST-UPDATED    "200808040000Z"
    ORGANIZATION    "Cisco Systems, Inc."
    CONTACT-INFO
            "Cisco Systems
            Customer Service

            Postal: 170 W Tasman Drive
            San Jose, CA  95134
            USA

            Tel: +1 800 553-NETS

            E-mail: cs-excelsior-dev@cisco.com"
    DESCRIPTION
        "This MIB module defines objects describing traffic controllers
        used by a service control entity.

        A service control entity is a network device which monitors and
        controls traffic. The service control enitity is used as a
        platform for different service control applications which may
        perform monitoring operations beyond packet counting and delve
        deeper into the contents of network traffic, such as deep packet
        inspection.
        It provides programmable stateful inspection of bidirectional
        traffic flows, maps these flows to users or subscribers, and can
        control traffic flow according to different attributes.

        A service control entity traffic controller can act as a rather
        simple policer or implement more complicated logic in
        controlling traffic, up to actual applicative attributes of the
        traffic itself.

        The global service controller is a controller component
        implemented by the service control entity, which acts as a
        rather simple policer for traffic transiting through the service
        control entity. A global service controller may be configured
        per service control entity interface with a configurable
        bandwidth limitation. The controller is responsible for the
        enforcement of the bandwith limitation configured in the service
        control entity."
    REVISION        "200808040000Z"
    DESCRIPTION
        "Initial version of this MIB module."
    ::= { ciscoMgmt 667 }


ciscoServiceControlMIBObjects  OBJECT IDENTIFIER
    ::= { ciscoServiceControllerMIB 0 }

ciscoServiceControlMIBConform  OBJECT IDENTIFIER
    ::= { ciscoServiceControllerMIB 1 }


cscGlobalControllersTable OBJECT-TYPE
    SYNTAX          SEQUENCE OF CscGlobalControllersEntry 
    MAX-ACCESS      not-accessible
    STATUS          current
    DESCRIPTION
        "This table contains data for each global service controller in
        the service control entity. The table has an expansion dependent
        relationship on the entPhysicalTable, containing zero or more
        rows for each physical entity."
    ::= { ciscoServiceControlMIBObjects 1 }

cscGlobalControllersEntry OBJECT-TYPE
    SYNTAX          CscGlobalControllersEntry
    MAX-ACCESS      not-accessible
    STATUS          current
    DESCRIPTION
        "This entry contains the operational data for the global service
        controller associated with the service control entity identified
        by its assigned entPhysicalIndex. Each entry uniquely identifies
        a global controller by its index. The"
    INDEX           {
                        entPhysicalIndex,
                        cscGlobalControllersIndex
                    } 
    ::= { cscGlobalControllersTable 1 }

CscGlobalControllersEntry ::= SEQUENCE {
        cscGlobalControllersIndex          Unsigned32,
        cscGlobalControllersId             Unsigned32,
        cscGlobalControllersDescription    SnmpAdminString,
        cscGlobalControllersBandwidthUnits INTEGER,
        cscGlobalControllersBandwidth      Unsigned32,
        cscGlobalControllersUtilization    Unsigned32
}

cscGlobalControllersIndex OBJECT-TYPE
    SYNTAX          Unsigned32 (1..4294967295)
    MAX-ACCESS      not-accessible
    STATUS          current
    DESCRIPTION
        "This object indicates an arbitrary integer-value that
        uniquely identifies a global service controller." 
    ::= { cscGlobalControllersEntry 1 }

cscGlobalControllersId OBJECT-TYPE
    SYNTAX          Unsigned32
    MAX-ACCESS      read-create
    STATUS          current
    DESCRIPTION
        "This object indicates the unique id assigned to this global
        controller by the service control entity." 
    ::= { cscGlobalControllersEntry 2 }

cscGlobalControllersDescription OBJECT-TYPE
    SYNTAX          SnmpAdminString (SIZE  (1..255))
    MAX-ACCESS      read-create
    STATUS          current
    DESCRIPTION
        "This object indicates a human readable string which is the name
        associated with this global service controller." 
    ::= { cscGlobalControllersEntry 3 }

cscGlobalControllersBandwidthUnits OBJECT-TYPE
    SYNTAX          INTEGER  {
                        kbps(1),
                        mbps(2)
                    }
    MAX-ACCESS      read-create
    STATUS          current
    DESCRIPTION
        "An enumerated value which identifies the units for
        cscGlobalControllersBandwidth value, such as 'kbps' (kilobit per
        second), 'mbps' (megabit per second), etc."
    DEFVAL          { kbps } 
    ::= { cscGlobalControllersEntry 4 }

cscGlobalControllersBandwidth OBJECT-TYPE
    SYNTAX          Unsigned32 (0..4294967295)
    MAX-ACCESS      read-create
    STATUS          current
    DESCRIPTION
        "This object indicates the bandwidth limitation for this global
        controller to enforce. The units of
        cscGlobalControllersBandwidth are indicated by the value of
        cscGlobalControllersBandwidthUnits." 
    ::= { cscGlobalControllersEntry 5 }

cscGlobalControllersUtilization OBJECT-TYPE
    SYNTAX          Unsigned32 (0..100)
    UNITS           "percent"
    MAX-ACCESS      read-create
    STATUS          current
    DESCRIPTION
        "This object specifies the percentage of utilized bandwidth
        of the controller out of the configured bandwidth limitation by
        the cscGlobalControllersBandwidth. For example, if
        cscGlobalControllersBandwidth = 1000 kbps and
        cscGlobalControllersUtilization = 65%, then the
        current utilization of this controller is 650 kbps." 
    ::= { cscGlobalControllersEntry 6 }
 

-- Conformance

ciscoServiceControlMIBCompliances  OBJECT IDENTIFIER
    ::= { ciscoServiceControlMIBConform 1 }

ciscoServiceControlMIBObjectGroups  OBJECT IDENTIFIER
    ::= { ciscoServiceControlMIBConform 2 }


ciscoServiceControlMIBCompliance MODULE-COMPLIANCE
    STATUS          current
    DESCRIPTION
        "The compliance statement for SNMP entities that implement
        version 1 of the Cisco Service Controller MIB."
    MODULE          -- this module
    MANDATORY-GROUPS { ciscoServiceControlMIBGlobalControllersObjectGroup }
    ::= { ciscoServiceControlMIBCompliances 1 }

ciscoServiceControlMIBGlobalControllersObjectGroup OBJECT-GROUP
    OBJECTS         {
                        cscGlobalControllersDescription,
                        cscGlobalControllersBandwidth,
                        cscGlobalControllersUtilization,
                        cscGlobalControllersBandwidthUnits,
                        cscGlobalControllersId
                    }
    STATUS          current
    DESCRIPTION
        "This group is a collection of objects that describes the
        global controllers statistics for service control entity."
    ::= { ciscoServiceControlMIBObjectGroups 1 }

END
