-- *****************************************************************
-- CLAB-DEF-MIB.my:
--
-- Mar 2005 Jun Yan
--
-- Initial Version: Mar 2005: MIB-CLABDEF-N-04.0018-3.pdf 
--
-- Copyright (c) 2005 by cisco Systems, Inc.
-- All rights reserved.
-- *****************************************************************

CLAB-DEF-MIB DEFINITIONS ::= BEGIN
IMPORTS
    MODULE-IDENTITY,
    OBJECT-TYPE,
    enterprises
                 FROM SNMPv2-SMI
    DocsX509ASN1DEREncodedCertificate
                 FROM DOCS-IETF-BPI2-MIB;
    cableLabs MODULE-IDENTITY
        LAST-UPDATED "200408041700Z" -- August 8, 2004
        ORGANIZATION "Cable Television Laboratories, Inc."
        CONTACT-INFO
                "Editor: Jean-Francois Mule
                Postal: Cable Television Laboratories, Inc.
                        858 Coal Creek Circle
                        Louisville, Colorado 80027-9750
                        U.S.A.
                Phone: +1 303-661-9100
                Fax: +1 303-661-9199
                E-mail: jfm@cablelabs.com
                        mibs@cablelabs.com"
        DESCRIPTION
                "This MIB module defines the namespace organization for the
                CableLabs enterprise OID registry.

                Copyright 1999-2004 Cable Television Laboratories, Inc.
                All rights reserved."

        REVISION "200408041700Z" -- August 8, 2004
        DESCRIPTION
                "This revision, published as CL-SP-MIB-CLABDEF-I04."
        ::= { enterprises 4491 }

    -- Sub-tree for Registrations
    clabFunction OBJECT IDENTIFIER ::= { cableLabs 1 }
    clabFuncMib2 OBJECT IDENTIFIER ::= { clabFunction 1 }
    clabFuncProprietary OBJECT IDENTIFIER ::= { clabFunction 2 }

    -- Sub-tree for Project Definitions
    clabProject OBJECT IDENTIFIER ::= { cableLabs 2 }
    clabProjDocsis OBJECT IDENTIFIER ::= { clabProject 1 }
    clabProjPacketCable OBJECT IDENTIFIER ::= { clabProject 2 }
    clabProjOpenCable OBJECT IDENTIFIER ::= { clabProject 3 }
    clabProjCableHome OBJECT IDENTIFIER ::= { clabProject 4 }

    -- Sub-tree for Global Security Definitions
    clabSecurity OBJECT IDENTIFIER ::= { cableLabs 3 }
    clabSecCertObject OBJECT IDENTIFIER ::= { clabSecurity 1 }

    --
    -- CableLabs DOCSIS Project Sub-tree Definitions
    --
    dsgMIB OBJECT IDENTIFIER
        -- DOCSIS Set-top Gateway (DSG) MIB module
        -- This object identifier points to the MIB module
        -- DOCSIS-SETTOP-GATEWAY-MIB, which is being deprecated by
        -- DSG-IF-MIB MIB module (dsgIfMib).
        -- Reference:
        -- CableLabs DOCSIS Set-top Gateway (DSG) Interface Specification
        ::= { clabProjDocsis 1 }

    docsLoadBalMib OBJECT IDENTIFIER
        -- DOCSIS MIB module defining the CMTS configuration parameters to
        -- support Load Balancing requirements."
        ::= { clabProjDocsis 2 }

    dsgIfMIB OBJECT IDENTIFIER
        -- DOCSIS Set-top Gateway (DSG) MIB module
        -- Obsoletes DOCSIS-SETTOP-GATEWAY-MIB Module (dsgMib)
        -- defined initially in DOCSIS Set-top Gateway (DSG) Interface
        -- Specification SP-DSG-I01-020228
        -- Reference:
        -- CableLabs DOCSIS Set-top Gateway (DSG) Interface Specification
        ::= { clabProjDocsis 3 }

    docsTestMIB OBJECT IDENTIFIER
        -- DOCSIS Test MIB module supporting programmable test features
        -- for DOCSIS 2.0 compliant Cable Modems (CM) and Cable Modems
        -- Termination Systems (CMTS).
        -- Reference:
        -- CableLabs DOCSIS 2.0 Testing MIB Specification
        ::= { clabProjDocsis 12 }

    sledMib OBJECT IDENTIFIER
        -- eDOCSIS MIB module supporting the Software Loopback Application
        -- for eDOCSIS (SLED).
        -- Reference:
        -- CableLabs eDOCSIS Specification
        ::= { clabProjDocsis 13 }

    --
    -- CableLabs CableHome Project Sub-tree Definitions
    -- Reference
    -- CableLabs CableHome Specification
    --
    cabhPsDevMib OBJECT IDENTIFIER
        -- CableHome MIB module defining the basic management objects for
        -- the Portal Services logical element of a CableHome compliant
        -- Residential Gateway device. The PS device parameters describe
        -- general PS Device attributes and behavior characteristics
        ::= { clabProjCableHome 1 }

    cabhSecMib OBJECT IDENTIFIER
        -- CableHome MIB module defining the basic management objects for
        -- the firewall and other security features of the Portal Services
        -- element.
        ::= { clabProjCableHome 2 }

    cabhCapMib OBJECT IDENTIFIER
        -- CableHome MIB module defining the basic management objects for
        -- the CableHome Addressing Portal (CAP) function of the Portal
        -- Services element.
        ::= { clabProjCableHome 3 }

    cabhCdpMib OBJECT IDENTIFIER
        -- This MIB module supplies the basic management objects for the
        -- CableHome DHCP Portal (CDP) function of the Portal Services
        -- element.
        ::= { clabProjCableHome 4 }

    cabhCtpMib OBJECT IDENTIFIER
        -- CableHome MIB module supporting the remote LAN diagnostic
        -- features provided by the CableHome Test Portal (CTP) function
        -- of the Portal Services element.
        ::= { clabProjCableHome 5 }

    cabhQosMib OBJECT IDENTIFIER
        -- CableHome MIB module defining management objects for the
        -- configuration and monitoring of CableHome prioritized QoS
        -- capability.
        ::= { clabProjCableHome 6 }

    cabhCsaMib OBJECT IDENTIFIER
        -- CableHome MIB module defining management objects for the
        -- configuration and monitoring of CableHome Commercial Service
        -- Annex.
        ::= { clabProjCableHome 7 }

    --
    -- CableLabs PacketCable Project Sub-tree Definitions
    --
    pktcMtaMib OBJECT IDENTIFIER
        -- PacketCable MIB module defining the basic management object for
        -- the Multimedia Terminal Adapter (MTA) devices compliant with
        -- PacketCable requirements.
        -- Reference
        -- CableLabs PacketCable MTA Device Provisioning Specification
        ::= { clabProjPacketCable 1 }

    pktcSigMib OBJECT IDENTIFIER
        -- PacketCable MIB module defining the basic management object for
        -- the PacketCable MTA Signaling protocols. This version of the MIB
        -- includes common signaling and Network Call Signaling (NCS)
        -- related signaling objects.
        -- Reference
        -- CableLabs PacketCable MTA Device Provisioning Specification
        ::= { clabProjPacketCable 2 }

    pktcEventMib OBJECT IDENTIFIER
        -- PacketCable MIB module defining the basic management objects for
        -- event reporting.
        -- Reference
        -- CableLabs PacketCable Management Event Specification
        ::= { clabProjPacketCable 3 }

    pktcSecurity OBJECT IDENTIFIER
        -- CableLabs OID reserved for security and used to specify errors
        -- that can be returned for the Kerberos KDC - Provisioning
        -- Server interface, or the MTA-CMS Kerberized IPsec interface, or
        -- the MTA-Provisioning Server Kerberized SNMPv3 interface.
        -- CableLabs PacketCable Security Specification
        ::= { clabProjPacketCable 4 }

    pktcLawfulIntercept OBJECT IDENTIFIER
        -- CableLabs OID reserved for the PacketCable Electronic
        -- Surveillance Protocol (PCESP) between the Delivery Function
        -- and Collection Function. This OID is used to define the ASN.1
        -- PCESP messages.
        -- CableLabs PacketCable Electronic Surveillance Protocol
        -- Specification
        ::= { clabProjPacketCable 5 }

    --
    -- Definition of CableLabs Security Certificate Objects
    --
    clabSrvcPrvdrRootCACert OBJECT-TYPE
        SYNTAX DocsX509ASN1DEREncodedCertificate
        MAX-ACCESS read-only
        STATUS current
        DESCRIPTION
                "The X509 DER-encoded CableLabs Service Provider Root CA
                Certificate."
        REFERENCE
                "CableLabs CableHome Specification;
                CableLabs PacketCable Security Specification."
        ::= { clabSecCertObject 1 }

    clabCVCRootCACert OBJECT-TYPE
        SYNTAX DocsX509ASN1DEREncodedCertificate
        MAX-ACCESS read-only
        STATUS current
        DESCRIPTION
                "The X509 DER-encoded CableLabs CVC Root CA Certificate."
        REFERENCE
                "CableLabs CableHome Specification;
                CableLabs PacketCable Security Specification."
        ::= { clabSecCertObject 2 }

    clabCVCCACert OBJECT-TYPE
        SYNTAX DocsX509ASN1DEREncodedCertificate
        MAX-ACCESS read-only
        STATUS current
        DESCRIPTION
                "The X509 DER-encoded CableLabs CVC CA Certificate."
        REFERENCE
                "CableLabs CableHome Specification;
                CableLabs PacketCable Security Specification."
        ::= { clabSecCertObject 3 }

    clabMfgCVCCert OBJECT-TYPE
        SYNTAX DocsX509ASN1DEREncodedCertificate
        MAX-ACCESS read-only
        STATUS current
        DESCRIPTION
                "The X509 DER-encoded Manufacturer CVC Certificate."
        REFERENCE
                "CableLabs CableHome Specification;
                CableLabs PacketCable Security Specification."
        ::= { clabSecCertObject 4 }

    clabMfgCACert OBJECT-TYPE
        SYNTAX DocsX509ASN1DEREncodedCertificate
        MAX-ACCESS read-only
        STATUS current
        DESCRIPTION
                "The X509 DER-encoded Manufacturer CA Certificate."
        REFERENCE
                "CableLabs CableHome Specification;
                CableLabs PacketCable Security Specification."
        ::= { clabSecCertObject 5 }

    END
