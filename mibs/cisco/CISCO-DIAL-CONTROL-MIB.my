-- *****************************************************************
-- The CISCO dial control mib. This is an extension to the RFC 2128.
--
-- Bibek Das, January, 1998
--
-- Copyright (c) 1998 by cisco Systems, Inc.
-- All rights reserved.
-- *****************************************************************
--
-- This mib is an extension to the RFC 2128
-- 
-- The RFC 2128 (Dial Control Mib) defines callHistoryTable, which is
-- the table that stores past call information. Unfortunately, the indices
-- to this table (callActiveSetupTime, callActiveIndex) are not appropriate
-- for the NMS to retrieve information on regular intervals.
-- 
-- The following changes in the RFC2128 will fix the INDEX of the
-- callHistoryTable. This will also make the mib useful for various types 
-- of calls, including ISDN data, voice, modem. VoIP etc. Right now, the 
-- NMS needs to poll three different mibs (CISCO-CALL-HISTORY-MIB.my, 
-- CISCO-POP-MGMT-MIB.my and the DIAL-CONTROL-MIB.my) for these calls.
--
-- We'll attempt to forward these changes to the ISDN working group
-- so that it may be discussed and approved for the next draft of the
-- RFC 2128.


CISCO-DIAL-CONTROL-MIB DEFINITIONS ::= BEGIN

IMPORTS
        MODULE-IDENTITY,
        OBJECT-TYPE
                FROM SNMPv2-SMI
        DisplayString,
        TimeStamp
                 FROM SNMPv2-TC
        MODULE-COMPLIANCE,
        OBJECT-GROUP
                FROM SNMPv2-CONF
        Unsigned32                  
		FROM CISCO-TC
        ciscoExperiment                  
		FROM CISCO-SMI
        AbsoluteCounter32 
		FROM DIAL-CONTROL-MIB
        InterfaceIndex
                FROM IF-MIB;

ciscoDialControlMib MODULE-IDENTITY
        LAST-UPDATED    "9801161546Z" -- January 16, 1998
        ORGANIZATION    "Cisco systems, Inc."
        CONTACT-INFO
            "        Bibek Das
             Postal: cisco Systems
                     170 West Tasman Drive
                     San Jose, CA 95134
                     U.S.A.
             Phone:  +1 408 526 5225
             E-mail: cs-isdn@cisco.com"
        DESCRIPTION
            "The MIB module to describe call history information for
             demand access and possibly other kinds of interfaces."
        ::= { ciscoExperiment 25 }


-- Cisco Dial Control Mib objects definitions

ciscoDialControlMibObjects OBJECT IDENTIFIER ::= { ciscoDialControlMib 1 }

--
-- the call history group
--

cCallHistory OBJECT IDENTIFIER ::= { ciscoDialControlMibObjects 4 }

-- cCallHistoryTable
-- Table to store the past call information. The Destination number
-- and the call connect and disconnect time, the disconnection cause
-- are stored. These calls could be circuit switched or they could
-- be virtual circuits. History of each and every call is stored,
-- of successful calls as well as of unsuccessful and rejected calls.
-- An entry will be created when a call is cleared.
-- The upper limit to the number of entries in this table is given
-- by callHistoryTableMaxLength, defined in RFC 2128.
-- The minimum time that an entry can be retained in this table is
-- given by callHistoryRetainTimer, defined in RFC 2128.

cCallHistoryTable OBJECT-TYPE
        SYNTAX      SEQUENCE OF CCallHistoryEntry
        MAX-ACCESS  not-accessible
        STATUS      current
        DESCRIPTION
            "A table containing information about specific
             calls to a specific destination."
        ::= { cCallHistory 3 }

cCallHistoryEntry OBJECT-TYPE
        SYNTAX      CCallHistoryEntry
        MAX-ACCESS  not-accessible
        STATUS      current
        DESCRIPTION
            "The information regarding a single Connection."
        INDEX       { cCallHistoryIndex }
        ::= { cCallHistoryTable 1 }


CCallHistoryEntry ::=
        SEQUENCE {
	    cCallHistoryIndex                     Unsigned32,
	    cCallHistorySetupTime                 TimeStamp,
            cCallHistoryPeerAddress               DisplayString,
            cCallHistoryPeerSubAddress            DisplayString,
            cCallHistoryPeerId                    INTEGER,
            cCallHistoryPeerIfIndex               INTEGER,
            cCallHistoryLogicalIfIndex            InterfaceIndex,
            cCallHistoryDisconnectCause           OCTET STRING,
            cCallHistoryDisconnectText            DisplayString,
            cCallHistoryConnectTime               TimeStamp,
            cCallHistoryDisconnectTime            TimeStamp,
            cCallHistoryCallOrigin                INTEGER,
            cCallHistoryChargedUnits              AbsoluteCounter32,
            cCallHistoryInfoType                  INTEGER,
            cCallHistoryTransmitPackets           AbsoluteCounter32,
            cCallHistoryTransmitBytes             AbsoluteCounter32,
            cCallHistoryReceivePackets            AbsoluteCounter32,
            cCallHistoryReceiveBytes              AbsoluteCounter32
        }

cCallHistoryIndex OBJECT-TYPE
        SYNTAX      Unsigned32 (1..4294967295)
        MAX-ACCESS  not-accessible
        STATUS      current
        DESCRIPTION
            "A monotonically increasing integer for the sole purpose of
             indexing call disconnection events.  When it reaches the 
             maximum value, an extremely unlikely event, the agent wraps 
             the value back to 1 and may flush existing entries."
        ::= { cCallHistoryEntry 1 }
 
cCallHistorySetupTime OBJECT-TYPE
        SYNTAX      TimeStamp
        MAX-ACCESS  read-only
        STATUS      current
        DESCRIPTION
            "The value of sysUpTime when the call setup was started.
             This will be useful for an NMS to sort the call history
             entry with call setup time. Also, this object
             can be useful in finding large delays between the time the
             call was started and the time the call was connected.
             For ISDN media, this will be the time when the setup
             message was received from or sent to the network.
             The value of this object is the same as callActiveSetupTime
             in the callActiveTable"
        ::= { cCallHistoryEntry 2 }

cCallHistoryPeerAddress OBJECT-TYPE
        SYNTAX      DisplayString
        MAX-ACCESS  read-only
        STATUS      current
        DESCRIPTION
            "The number this call was connected to. If the number is
             not available, then it will have a length of zero."
        ::= { cCallHistoryEntry 3 }

cCallHistoryPeerSubAddress OBJECT-TYPE
        SYNTAX      DisplayString
        MAX-ACCESS  read-only
        STATUS      current
        DESCRIPTION
            "The subaddress this call was connected to. If the subaddress
             is undefined or not available, this will be a zero length
             string."
        ::= { cCallHistoryEntry 4 }
cCallHistoryPeerId OBJECT-TYPE
        SYNTAX      INTEGER (0..2147483647)
        MAX-ACCESS  read-only
        STATUS      current
        DESCRIPTION
            "This is the Id value of the peer table entry
             to which this call was made. If a peer table entry
             for this call does not exist, the value of this object
             will be zero."
        ::= { cCallHistoryEntry 5 }

cCallHistoryPeerIfIndex OBJECT-TYPE
        SYNTAX      INTEGER (0..2147483647)
        MAX-ACCESS  read-only
        STATUS      current
        DESCRIPTION
            "This is the ifIndex value of the peer table entry
             to which this call was made. If a peer table entry
             for this call does not exist, the value of this object
             will be zero."
        ::= { cCallHistoryEntry 6 }

cCallHistoryLogicalIfIndex OBJECT-TYPE
        SYNTAX      InterfaceIndex
        MAX-ACCESS  read-only
        STATUS      current
        DESCRIPTION
            "This is the ifIndex value of the logical interface through
             which this call was made. For ISDN media, this would be
             the ifIndex of the B channel which was used for this call."
        ::= { cCallHistoryEntry 7 }

cCallHistoryDisconnectCause OBJECT-TYPE
        SYNTAX      OCTET STRING (SIZE (0..4))
        MAX-ACCESS  read-only
        STATUS      current
        DESCRIPTION
            "The encoded network cause value associated with this call.

             The value of this object will depend on the interface type
             as well as on the protocol and protocol version being
             used on this interface. Some references for possible cause
             values are given below."
        REFERENCE
            "- Bellcore SR-NWT-001953, Generic Guidelines for
               ISDN Terminal Equipment On Basic Access Interfaces,
               chapter 5.2.5.8.
             - Bellcore SR-NWT-002343, ISDN Primary Rate Interface
               Generic Guidelines for Customer Premises Equipment,
               chapter 8.2.5.8.
             - ITU-T Q.931, Appendix I.
             - ITU-T X.25, CAUSE and DIAGNOSTIC field values.
             - German Telekom FTZ 1TR6, chapter 3.2.3.4.4.4."
        ::= { cCallHistoryEntry 8 }

cCallHistoryDisconnectText OBJECT-TYPE
        SYNTAX      DisplayString
        MAX-ACCESS  read-only
        STATUS      current
        DESCRIPTION
            "ASCII text describing the reason for call termination.

             This object exists because it would be impossible for
             a management station to store all possible cause values
             for all types of interfaces. It should be used only if
             a management station is unable to decode the value of
             dialCtlPeerStatsLastDisconnectCause."
        ::= { cCallHistoryEntry 9 }

cCallHistoryConnectTime OBJECT-TYPE
        SYNTAX      TimeStamp
        MAX-ACCESS  read-only
        STATUS      current
        DESCRIPTION
            "The value of sysUpTime when the call was connected."
        ::= { cCallHistoryEntry 10 }

cCallHistoryDisconnectTime OBJECT-TYPE
        SYNTAX      TimeStamp
        MAX-ACCESS  read-only
        STATUS      current
        DESCRIPTION
            "The value of sysUpTime when the call was disconnected."
        ::= { cCallHistoryEntry 11 }

cCallHistoryCallOrigin OBJECT-TYPE
        SYNTAX      INTEGER {
            originate(1),
            answer(2),
            callback(3)
        }
        MAX-ACCESS  read-only
        STATUS      current
        DESCRIPTION
            "The call origin."
        ::= { cCallHistoryEntry 12 }

cCallHistoryChargedUnits OBJECT-TYPE
        SYNTAX      AbsoluteCounter32
        MAX-ACCESS  read-only
        STATUS      current
        DESCRIPTION
            "The number of charged units for this connection.
             For incoming calls or if charging information is
             not supplied by the switch, the value of this object
             will be zero."
        ::= { cCallHistoryEntry 13 }

cCallHistoryInfoType OBJECT-TYPE
        SYNTAX      INTEGER {
            other(1),                   -- e.g. for non-isdn media
            speech(2),
            unrestrictedDigital(3),     -- 64k/s data
            unrestrictedDigital56(4),   -- with 56k rate adaption
            restrictedDigital(5),
            audio31(6),                 -- 3.1 kHz audio
            audio7(7),                  -- 7 kHz audio
            video(8),
            packetSwitched(9),
            fax(10)
        }
        MAX-ACCESS  read-only
        STATUS      current
        DESCRIPTION
            "The information type for this call."
        ::= { cCallHistoryEntry 14 }

cCallHistoryTransmitPackets OBJECT-TYPE
        SYNTAX      AbsoluteCounter32
        MAX-ACCESS  read-only
        STATUS     current
        DESCRIPTION
            "The number of packets which were transmitted while this
             call was active."
        ::= { cCallHistoryEntry 15 }

cCallHistoryTransmitBytes OBJECT-TYPE
        SYNTAX      AbsoluteCounter32
        MAX-ACCESS  read-only
        STATUS      current
        DESCRIPTION
            "The number of bytes which were transmitted while this
             call was active."
        ::= { cCallHistoryEntry 16 }

cCallHistoryReceivePackets OBJECT-TYPE
        SYNTAX      AbsoluteCounter32
        MAX-ACCESS  read-only
        STATUS      current
        DESCRIPTION
            "The number of packets which were received while this
             call was active."
        ::= { cCallHistoryEntry 17 }

cCallHistoryReceiveBytes OBJECT-TYPE
        SYNTAX      AbsoluteCounter32
        MAX-ACCESS  read-only
        STATUS      current
        DESCRIPTION
            "The number of bytes which were received while this
             call was active."
        ::= { cCallHistoryEntry 18 }


-- conformance information

ciscoDialControlMibConformance OBJECT IDENTIFIER ::=
                                { ciscoDialControlMib 3 }

ciscoDialControlMibCompliances OBJECT IDENTIFIER ::=
                                { ciscoDialControlMibConformance 1 }

ciscoDialControlMibGroups      OBJECT IDENTIFIER ::=
                                { ciscoDialControlMibConformance 2 }

-- compliance statements

ciscoDialControlMibCompliance MODULE-COMPLIANCE
        STATUS      current
        DESCRIPTION
            "The compliance statement for entities which
             implement the DIAL CONTROL MIB"
        MODULE      -- this module
        MANDATORY-GROUPS
            { cCallHistoryGroup }
        ::= { ciscoDialControlMibCompliances 1 }

-- units of conformance


cCallHistoryGroup OBJECT-GROUP
        OBJECTS {
	    cCallHistorySetupTime,
            cCallHistoryPeerAddress,
            cCallHistoryPeerSubAddress,
            cCallHistoryPeerId,
            cCallHistoryPeerIfIndex,
            cCallHistoryLogicalIfIndex,
            cCallHistoryDisconnectCause,
            cCallHistoryDisconnectText,
            cCallHistoryConnectTime,
            cCallHistoryDisconnectTime,
            cCallHistoryCallOrigin,
            cCallHistoryChargedUnits,
            cCallHistoryInfoType,
            cCallHistoryTransmitPackets,
            cCallHistoryTransmitBytes,
            cCallHistoryReceivePackets,
            cCallHistoryReceiveBytes
        }
        STATUS      current
        DESCRIPTION
            "A collection of objects providing the Call History
             capability."
        ::= { ciscoDialControlMibGroups 1 }



END
