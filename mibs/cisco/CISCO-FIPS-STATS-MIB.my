-- *------------------------------------------------------------------
-- * CISCO-FIPS-STATS-MIB.my:  The CISCO FIPs Status MIB.
-- *
-- *
-- * Copyright (c) 2002-2003 by Cisco Systems, Inc.
-- * All rights reserved.
-- *
-- *------------------------------------------------------------------

CISCO-FIPS-STATS-MIB DEFINITIONS ::= BEGIN
IMPORTS
	MODULE-IDENTITY, OBJECT-TYPE
		FROM SNMPv2-SMI
	OBJECT-GROUP, MODULE-COMPLIANCE
		FROM SNMPv2-CONF
	ciscoMgmt
                FROM CISCO-SMI;

ciscoFipsStatsMIB       MODULE-IDENTITY
	LAST-UPDATED	"200303100000Z"
	ORGANIZATION	"Cisco Systems, Inc."
	CONTACT-INFO	
	   "Cisco Systems
            170 W Tasman Drive
            San Jose, CA  95134
            USA

            Tel: +1 800 553-NETS
            E-mail: cs-fips-stats-mib@cisco.com"

	DESCRIPTION
	    "The Federal Information Processing Standards (FIPS) 
             power-up self-test status MIB module"
          
      	REVISION        "200303100000Z"
        DESCRIPTION
             "The initial version of this MIB."
	::= { ciscoMgmt 999999 }

ciscoFipsStatsMIBNotifs  OBJECT IDENTIFIER ::=  
                                 { ciscoFipsStatsMIB 0 }
ciscoFipsStatsMIBObjects OBJECT IDENTIFIER ::=  
                                 { ciscoFipsStatsMIB 1 }
ciscoFipsStatsMIBConform OBJECT IDENTIFIER ::=  
                                 { ciscoFipsStatsMIB 2 }

-- +++++++++++++++++++++++++++++++++++++++++++++++++++++++
-- MIB Objects
-- +++++++++++++++++++++++++++++++++++++++++++++++++++++++
cfipsStats OBJECT IDENTIFIER ::= { ciscoFipsStatsMIBObjects 1 }

cfipsStatsGlobal OBJECT IDENTIFIER ::= { cfipsStats 1 }

cfipsPostStatus           	OBJECT-TYPE
	SYNTAX			INTEGER {
                                         running (1),
                                         passed (2),
                                         failed (3),
                                         notAvailable (4)
                                         }
	MAX-ACCESS		read-only
	STATUS			current
	DESCRIPTION
	       "Indicates whether or not the FIPS power-up self-test passed."
	DEFVAL			{ notAvailable }
	::= { cfipsStatsGlobal 1 }

ciscoFipsStatsMIBCompliances OBJECT IDENTIFIER
   ::= { ciscoFipsStatsMIBConform 1 }
ciscoFipsStatsMIBGroups  OBJECT IDENTIFIER 
   ::= { ciscoFipsStatsMIBConform 2 }
  
ciscoFipsStatsMIBCompliance MODULE-COMPLIANCE
   STATUS         current
   DESCRIPTION
      "The compliance statement for agents which 
       implement the CISCO FIPs Status MIB."
   MODULE
   MANDATORY-GROUPS { 
      ciscoFipsStatsMIBGroup
   }
   ::= { ciscoFipsStatsMIBCompliances 1 }


ciscoFipsStatsMIBGroup OBJECT-GROUP
	OBJECTS
	{
          cfipsPostStatus
	}
	STATUS 	current
	DESCRIPTION
	       "The objects for FIPS configuration."
	::= { ciscoFipsStatsMIBGroups 1 }

END
