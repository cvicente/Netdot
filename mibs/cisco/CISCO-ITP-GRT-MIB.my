-- *****************************************************************   
-- CISCO-ITP-GRT-MIB: ITP Gateway Signalling Point Routing Table
--
-- September 2002, John Linton, Shekhar Acharya
--
-- Copyright (c) 2002-2003 by Cisco Systems, Inc.
-- All rights reserved.
-- *****************************************************************
--
-- *****************************************************************
CISCO-ITP-GRT-MIB DEFINITIONS ::= BEGIN

IMPORTS
        cgspCLLICode,
        cgspEventSequenceNumber,
        cgspInstNetwork
                FROM CISCO-ITP-GSP-MIB
        
        Counter32,  
        Gauge32,
        Integer32,
        MODULE-IDENTITY,
        NOTIFICATION-TYPE,
        OBJECT-TYPE,
        Unsigned32
                FROM SNMPv2-SMI
                
        RowStatus,
        TimeStamp,
        TruthValue 
                FROM SNMPv2-TC

        MODULE-COMPLIANCE,
        NOTIFICATION-GROUP,
        OBJECT-GROUP
                FROM SNMPv2-CONF
         
        CItpTcLinksetId,
        CItpTcPointCode,
        CItpTcQos,
        CItpTcRouteTableName, 
        CItpTcTableLoadStatus,
        CItpTcURL
                FROM CISCO-ITP-TC-MIB
       
        ciscoMgmt
                FROM CISCO-SMI;        
                
ciscoGrtMIB MODULE-IDENTITY
        LAST-UPDATED    "200303030000Z"
        ORGANIZATION    "Cisco Systems, Inc."
        CONTACT-INFO
                "       Cisco Systems, Inc
                        Customer Service

                Postal: 170 W. Tasman Drive
                        San Jose, CA  95134
                        USA

                   Tel: +1 800 553-NETS

                E-mail: cs-ss7s@cisco.com"
        DESCRIPTION
          "This MIB is for managing information required to 
           route messages transported over Signalling System 
           No. 7 (SS7) Network via Cisco IP Transfer
           Point.  
           
           The Cisco IP Transfer Point (ITP) is a hardware 
           and software solution that transports SS7 traffic 
           using IP.  Each ITP node provides the functions
           necessary to act as a SS7 signalling point.  Each 
           signalling point is connected to other signalling 
           point using IP based or traditional TDM links.
           
           The relevant ITU documents describing this technology 
           are the ITU Q series, including ITU Q.700: Introduction
           to CCITT Signalling System No. 7 and ITU Q.701 
           Functional description of the message transfer part
           (MTP) of Signalling System No. 7.
           

           Definitions and overview:
           
           Route:
           A route consists of one or more linksets used to transport
           MTP3 Message Signal Units(MSU) between signalling points.  
           A route is an association between a destination point 
           code(DPC) and a linkset, i.e., a linkset that can be used
           to send an MSU to the given DPC.
           
           Routeset:
           A routeset is a set of routes to a given DPC.  Each route
           within a routeset is on a possible path toward the DPC.
           Each route within the routeset has associated with it a
           route priority.
           
           In the following simple configuration, two routes exist
           that can be used to transport MSUs from STP1 to STP4.
           
             ---------         STP1-STP2         --------- 
             - STP1  ----------------------------- STP2  - 
             ---------                           --------- 
                 |                                   |
                 | STP1-STP3               STP2-STP4 |
                 |                                   |
             ---------         STP3-STP4         --------- 
             - STP3  ----------------------------- STP4  - 
             ---------                           --------- 
           
           Routeset on STP1 for DPC = STP4:
               STP1-STP2,
               STP1-STP3

           
           Linkset:
           A linkset is a set of signalling links connecting
           two signalling points.
           
           Combined Linkset: 
           Two linksets with equal number of links and capacity
           that form routes of equal priority to a given DPC are
           called Combined Linksets.  It is primarily used for
           load sharing and redundancy.  In the following, example,
           linksets 'SSP1-STP1' and 'SSP1-STP2' form a combined 
           linsket.
             
              
                   SSP1-STP1             ---------
                |------------------------- STP1  -
                |                        ---------
               - - 
             -     -
            -  SSP1 -  
             -     -
               - - 
                |  SSP1-STP2            ---------
                |------------------------ STP2  -
                                        ---------
           
           Routing:  
           The routing of SS7 Message signalling Units(MSU) is based 
           on the DPC.  Message Signalling Units are sent from an
           originating point code(OPC) to DPC.  Each MSU will 
           traverse one or more linksets as it is routed to its 
           final destination.  When an MSU arrives at a signalling
           point and the DPC does not match the signalling point's
           point code the MSU must be directed toward the DPC.  Each
           signalling point has enough routing information to 
           determine which linkset should be used to transmit the
           MSU toward its final destination.
           
           Route statement:  
           Each ITP Signalling Point has route statements needed to
           determine which linkset should be used to transmit 
           message signalling units to destinations.  Each route
           statement consists of a destination, a priority and a
           linkset name.  The destination is specified as a 
           combination of DPC and mask.  The priority, also know
           as cost, is used to define the order in which the routes
           are selected.  The linkset name specifies which linkset
           to use to reach the destination.
           
           Route table:  
           Each ITP Signalling Point has a table of routes.  
           These route entries are used to determine which linkset
           should be selected to transmit message signalling units 
           to a given destination.  
           
           There are two basic type of routing.  The first type
           is fully-qualified and uses all bits of the target DPC.  
           The other type is summary routing that uses a subset
           of the bits in the target DPC and is used to represent 
           groups of point codes rather than a single point code.
           
           Example of route table entries.
           
           Example 1: variant = ITU
           
           DPC/MASK  Priority  Linkset-name
           --------  --------  -----------------------
           5.5.5/14  3         STP1-STP2
           5.5.5/14  7         STP1-STP3

           Description: Two route table entries that define a
           primary route using linkset 'STP1-STP2' and an alternate
           route using linkset 'STP1-STP3' to point-code 5.5.5.
           
           Example 2: variant = ITU
           
           DPC/MASK  Priority  Linkset-name
           --------  --------  -----------------------
           5.5.5/14  3         STP1-STP2
           5.5.5/14  3         STP1-STP3
           5.5.5/14  7         STP1-STP4

           Description: Two route table entrys that define a
           combined linkset consisting of linkset 'STP1-STP2' and
           'STP1-STP3' to point code 5.5.5.  An alternate route is
           also defined using linkset 'STP1-STP4'.
           
           Example 3: variant = ANSI
           
           DPC/MASK  Priority  Linkset-name
           --------  --------  -----------------------
           5.5.0/16  3         STP1-STP2
           
           Description: A route table entry that defines routing
           to a cluster.  The cluster represents all point codes
           in the range from 5.5.0-5.5.255.
           
           Example 4: variant = ANSI
           
           DPC/MASK  Priority  Linkset-name
           --------  --------  -----------------------
           5.5.0/16  3         STP1-STP3
           5.5.5/24  3         STP1-STP2
           

           Description: The mixing of fully-qualified and summary
           route table entrys allow for different routes to be
           defined for certain DPC in a cluster.  In this 
           configuration, the fully-qualified route will be the 
           primary and the summary route will act as a backup.
                            
           Route table:  
           A group of route table entrys used to route MSU for a 
           particular instance of a signalling point.
           
           A sample route table.

           DPC/MASK  Priority  Linkset-name
           --------  --------  -----------------------
           0.0.0/0   7         STP1-STP4
           5.5.0/16  3         STP1-STP3
           5.5.5/24  3         STP1-STP2
           .
           .
           122.5.5   5         STP1-STP2
           .
           .
           243.200.1 6         STP1-STP3
           "
           
                
        REVISION        "200303030000Z"
        DESCRIPTION
                "Initial version of this MIB module."
        ::= { ciscoMgmt 334 }

-- Top-level structure of the MIB

ciscoGrtNotifications  OBJECT IDENTIFIER ::= { ciscoGrtMIB  0 }
ciscoGrtMIBObjects     OBJECT IDENTIFIER ::= { ciscoGrtMIB  1 }
ciscoGrtMIBConform     OBJECT IDENTIFIER ::= { ciscoGrtMIB  2 }


cgrtScalars   OBJECT IDENTIFIER ::= { ciscoGrtMIBObjects 1 }
cgrtObjects   OBJECT IDENTIFIER ::= { ciscoGrtMIBObjects 2 }

--  *************************************************************
--  *                                                           *
--  * SP - Scalers                                              *
--  *                                                           *
--  *************************************************************
cgrtRouteMaxDynamic              OBJECT-TYPE
    SYNTAX                       Integer32 (100..1000)
    MAX-ACCESS                   read-write
    STATUS                       current
    DESCRIPTION
            "The maximum number of dynamic SS7 routes. This
             object is used to limit the size of the route table
             by preventing unbounded growth of dynamic entries.
             Dynamic entries are created when certain MTP3 
             management messages are received or sent. The removal 
             of dynamic routes is performed periodically  and the
             older dynamic routes are removed until the specified 
             number is reached."  
    ::= { cgrtScalars  7 }
    
cgrtDestNotifDelayTime           OBJECT-TYPE
    SYNTAX                       Unsigned32 (0..60)
    UNITS                        "seconds"
    MAX-ACCESS                   read-write
    STATUS                       current 
    DESCRIPTION
        "This object specifies the maximum amount of time to delay
         before generating the ciscoGrtDestStateChange notification.
         The delay is introduced to allow multiple destination state 
         changes to be bundled into a single notification.
         
         If the value of this object is equal to 0, the device will 
         generate ciscoGrtDestStateChange notification as each route 
         changes states.

         If the value of this object is greater than 0, the device 
         will not generate notifications as destinations change state. 
         As each destination changes state they are accumulated until
         the time specified in cgrtDestNotifDelayTime has elapsed 
         or enough state changes have been accumulated to fill up the 
         cgrtDestNotifChanges object.
         
         This object is ignored by the agent when the
         cgrtDestNotifEnabled object is set to the 'false' 
         value."
    ::= { cgrtScalars 11 }

cgrtDestNotifWindowTime          OBJECT-TYPE
    SYNTAX                       Integer32 (30..900)
    UNITS                        "seconds"
    MAX-ACCESS                   read-write
    STATUS                       current 
    DESCRIPTION
        "This object specifies the time interval used to monitor
         the rate of destination state changes notifications.  This 
         object in combination with cgrtDestNotifMaxPerWindow is
         used to determine the notification transit rate and 
         suppress destination state notifications." 
    ::= { cgrtScalars 12 }
    
cgrtDestNotifMaxPerWindow        OBJECT-TYPE
    SYNTAX                       Integer32 (10..9000)
    MAX-ACCESS                   read-write
    STATUS                       current 
    DESCRIPTION
        "This object specifies the maximum number of destination
         state changes that can occur in the time interval 
         specified in the cgrtDestNotifWindowTime object.  
         If additional state changes can occur in the specified
         time interval the notifications are suppressed."
    ::= { cgrtScalars 13 }
    
cgrtDestNotifEnabled             OBJECT-TYPE
     SYNTAX                      TruthValue
     MAX-ACCESS                  read-write
     STATUS                      current
     DESCRIPTION          
         "A control to enable or disable ciscoGrtDestStateChange
          notifications as follows:
        'true'  Indicates that the ciscoGrtDestStateChange 
                notification should be generated when the state of 
                any destination changes. That is, the notification
                generation is enabled.
        'false' Indicates that ciscoGrtDestStateChange
                notification generation is disabled."
     DEFVAL { false }
    ::= { cgrtScalars 14 }
    
cgrtMgmtNotifDelayTime           OBJECT-TYPE
    SYNTAX                       Unsigned32 (0..60)
    UNITS                        "seconds"
    MAX-ACCESS                   read-write
    STATUS                       current
    DESCRIPTION
        "This object specifies the maximum amount of time to delay
         before generating the ciscoGrtMgmtStateChange notification.
         The delay is introduced to allow multiple route state 
         changes to be bundled into a single notification.
         
         If the value of this object is equal to 0, the device will 
         generate ciscoGrtMgmtStateChange notification as each route 
         changes states.

         If the value of this object is greater than 0, the device 
         will not generate notifications as routes change state. 
         As routes change state they are accumulated until the time
         specified in cgrtMgmtNotifDelayTime has elapsed or 
         enough state changes have been accumulated to fill up the 
         cgrtRouteNotifChanges object.
         
         This object is ignored by the agent when the
         cgrtMgmtNotifEnabled object is set to the 'false' value."
    ::= { cgrtScalars 16 }
    
cgrtMgmtNotifWindowTime          OBJECT-TYPE
    SYNTAX                       Integer32 (30..900)
    UNITS                        "seconds"
    MAX-ACCESS                   read-write
    STATUS                       current 
    DESCRIPTION
        "This object specifies the time interval used to monitor
         the rate of route state changes notifications.  This 
         object in combination with cgrtMgmtNotifMaxPerWindow is
         used to determine the notification transit rate and suppress
         route management state notifications." 
    ::= { cgrtScalars 17 }

cgrtMgmtNotifMaxPerWindow        OBJECT-TYPE
    SYNTAX                       Integer32 (10..9000)
    MAX-ACCESS                   read-write
    STATUS                       current 
    DESCRIPTION
        "This object specifies the maximum number of route
         management state changes that can occur in the time 
         interval specified in the cgrtMgmtNotifWindowTime
         object.  If additional state changes can occur in
         the specified time interval the notifications 
         are suppressed."
    ::= { cgrtScalars 18 }
    
cgrtMgmtNotifEnabled             OBJECT-TYPE
     SYNTAX                      TruthValue
     MAX-ACCESS                  read-write
     STATUS                      current
     DESCRIPTION          
        "A control to enable or disable ciscoGrtMgmtStateChange
          notifications as follows:
        'true'  Indicates that the ciscoGrtMgmtStateChange 
                notification should be generated when the state
                of any route changes. That is, the notification
                generation is enabled.
        'false' Indicates that ciscoGrtMgmtStateChange
                notification generation is disabled."
     DEFVAL { false }
    ::= { cgrtScalars 19 }
    
cgrtRouteTableLoadNotifEnabled   OBJECT-TYPE
     SYNTAX                      TruthValue
     MAX-ACCESS                  read-write
     STATUS                      current
     DESCRIPTION          
         "A control to enable or disable ciscoGrtRouteTableLoad
          notifications as follows:
        'true'  Indicates that the ciscoGrtRouteTableLoad
                notification should be generated when the load
                operations is started or completed.  That is,
                the notification generation is enabled.
        'false' Indicates that ciscoGrtRouteTableLoad notification
                generation is disabled."
     DEFVAL { false }
    ::= { cgrtScalars 20 }
    
cgrtDynamicRoutes                OBJECT-TYPE
    SYNTAX                       Gauge32
    MAX-ACCESS                   read-only
    STATUS                       current
    DESCRIPTION
            "The number of dynamic route entries created in
             response to MTP3 management messages.  The 
             maximum number for dynamic route entries is defined
             by the cgrtRouteMaxDynamic object.  When a MTP3 
             management message is received and this limit is 
             reached the request is dropped.  The 
             cgrtDynamicRoutesDropped object will be incremented
             in these situations."
             
    ::= { cgrtScalars  21 }

cgrtDynamicRoutesDropped         OBJECT-TYPE
    SYNTAX                       Counter32
    MAX-ACCESS                   read-only
    STATUS                       current
    DESCRIPTION
            "The number of dynamic route entries that could not
             be created because the limit specified by the 
             cgrtRouteMaxDynamic object had been reached."
             
    ::= { cgrtScalars  22 }

--  *************************************************************
--  *                                                           *
--  * Route Table information per instance of signalling point  *
--  *                                                           *
--  *************************************************************
cgrtInstTable                     OBJECT-TYPE
    SYNTAX                        SEQUENCE OF CgrtInstEntry 
    MAX-ACCESS                    not-accessible
    STATUS                        current
    DESCRIPTION
          "A route table exist per instance of signalling point.
           This table defines the routes defined for a particular
           instance." 
    ::= { cgrtObjects  1 }

cgrtInstEntry                     OBJECT-TYPE
    SYNTAX                        CgrtInstEntry 
    MAX-ACCESS                    not-accessible
    STATUS                        current
    DESCRIPTION
            "A collection of route statements used to 
             forward packets to requested destinations.  Each 
             table entry represents a route statement 
             that was either configured or added in response
             to events in the network."
    INDEX   { cgspInstNetwork   -- shared index
    }
    ::= { cgrtInstTable  1 }

CgrtInstEntry  ::= SEQUENCE {
    cgrtInstLastChanged             TimeStamp,
    cgrtInstLastLoadTime            TimeStamp,
    cgrtInstLoadStatus              CItpTcTableLoadStatus,
    cgrtInstTableName               CItpTcRouteTableName,
    cgrtInstLastURL                 CItpTcURL,
    cgrtInstNumberDestinations      Gauge32,
    cgrtInstNumberRoutes            Gauge32
}

cgrtInstLastChanged               OBJECT-TYPE
    SYNTAX                        TimeStamp 
    MAX-ACCESS                    read-only
    STATUS                        current
    DESCRIPTION
            "The value of sysUpTime at the time of the last
             creation or deletion of an entry in the route table
             defined for this signalling point.
             If the local network management subsystem is 
             re-initialized, then this object contains the 
             sysUpTime at the time when this occurred. This value 
             can be used to prevent unnecessary walks of the
             cgrtRouteTable."
    ::= {  cgrtInstEntry 1 }
    
cgrtInstLastLoadTime              OBJECT-TYPE
    SYNTAX                        TimeStamp 
    MAX-ACCESS                    read-only
    STATUS                        current
    DESCRIPTION
            "The value of sysUpTime at the time of the last
             load of the route table using file format."
    ::= {  cgrtInstEntry 2 }
    
cgrtInstLoadStatus                OBJECT-TYPE
    SYNTAX                        CItpTcTableLoadStatus 
    MAX-ACCESS                    read-only
    STATUS                        current
    DESCRIPTION
            "The status of the current load or status from
             the prior load operation.  This object will have
             a value of loadInProgress while the load operation
             is in progress.  The cgrtInstLastLoadTime contains
             a timestamp indicating when the load operation is
             completed."
    ::= { cgrtInstEntry 3 }
    
cgrtInstTableName                 OBJECT-TYPE
    SYNTAX                        CItpTcRouteTableName 
    MAX-ACCESS                    read-only
    STATUS                        current
    DESCRIPTION
            "The system generated name for the route table
             for this signalling point instance."
    ::= { cgrtInstEntry 4 }

cgrtInstLastURL                   OBJECT-TYPE
    SYNTAX                        CItpTcURL
    MAX-ACCESS                    read-only
    STATUS                        current
    DESCRIPTION
            "The url used to load route table."
    ::= { cgrtInstEntry 5 }
    
cgrtInstNumberDestinations        OBJECT-TYPE
    SYNTAX                        Gauge32
    UNITS                         "entries"
    MAX-ACCESS                    read-only
    STATUS                        current
    DESCRIPTION
            "The number of destination in the cgrtDestTable 
             Table." 
    ::= { cgrtInstEntry 6}
    
cgrtInstNumberRoutes              OBJECT-TYPE
    SYNTAX                        Gauge32
    UNITS                         "entries"
    MAX-ACCESS                    read-only
    STATUS                        current
    DESCRIPTION
            "The number of routes in the cgrtRouteTable Table." 
    ::= { cgrtInstEntry 7}

--  *************************************************************
--  *                                                           *
--  * Destination Table                                         *
--  *                                                           *
--  *************************************************************
cgrtDestTable                     OBJECT-TYPE
    SYNTAX                        SEQUENCE OF CgrtDestEntry 
    MAX-ACCESS                    not-accessible
    STATUS                        current
    DESCRIPTION
          "The destination table provides state information on
           the ability to route MTP packets to a particular
           destination point code."
    ::= { cgrtObjects  2 }

cgrtDestEntry                     OBJECT-TYPE
    SYNTAX                        CgrtDestEntry 
    MAX-ACCESS                    not-accessible
    STATUS                        current
    DESCRIPTION
            "Each table entry represents a specific destination
             point code(DPC)."
             
    INDEX   { cgspInstNetwork,  -- shared index
              cgrtRouteDpc,     -- shared index 
              cgrtRouteMask     -- shared index 
    }
    ::= { cgrtDestTable  1 }

CgrtDestEntry  ::= SEQUENCE {
    cgrtDestStatus               INTEGER,
    cgrtDestCongestion           Unsigned32
}

cgrtDestStatus                    OBJECT-TYPE
    SYNTAX                        INTEGER {
                                           unknown(1),
                                           accessible(2),
                                           inaccessible(3),
                                           restricted(4)
                                  }
    MAX-ACCESS                    read-only
    STATUS                        current
    DESCRIPTION
            "List of the possible route state values.
                'unknown'       : A destination state of unknown 
                occurs when the destination is a summary route.  
                Unknown state is presented to indicate the 
                protocols do not exchange state information for
                summary routes in certain configurations.
                
                'accessible'    : The destination can be reached by 
                one or more routes specified for the destination. 
                When summary routing is enabled, a destination 
                status will also depend on route table entrys that
                specify less specific matches.  See Example 4 in 
                the DESCRIPTION section for such a configuration. 

                'inaccessible'  : Destination can not be reached by
                any route known to this signalling point.
                
                'restricted'    : Traffic has been restricted from 
                being sent to the destination.  The restricted state
                indicates that the primary route for the destination
                is unavailable or that it is impacted by some network
                event or failure of resource."
    ::= { cgrtDestEntry  1 }
    
cgrtDestCongestion                OBJECT-TYPE
    SYNTAX                        Unsigned32 (0..3)
    MAX-ACCESS                    read-only
    STATUS                        current
    DESCRIPTION
            "The congestion status of this destination.  The value
             indicates congestion on one or more links in one 
             of the linksets used to route traffic to the signalling
             point specified by the cgrtRouteDpc object.
             0 is the least congestion level, 3 is the highest
             congestion level."
    REFERENCE
            "ITU Q.704 Signalling network functions and messages.
            ANSI T1.111 Telecommunications - Signalling system
            No. 7 (SS7)-Signalling network functions and messages
            2.3.5.2."
    ::= { cgrtDestEntry  2 }
    
--  *************************************************************
--  *                                                           *
--  * SP - Route Table                                          *
--  *                                                           *
--  *************************************************************

cgrtRouteTable                    OBJECT-TYPE
    SYNTAX                        SEQUENCE OF CgrtRouteEntry 
    MAX-ACCESS                    not-accessible
    STATUS                        current
    DESCRIPTION
          "The route table for determining the linkset that a
           packet must traverse to arrive at its destination 
           given by the destination point code."
    ::= { cgrtObjects 3 }

cgrtRouteEntry                    OBJECT-TYPE
    SYNTAX                        CgrtRouteEntry 
    MAX-ACCESS                    not-accessible
    STATUS                        current
    DESCRIPTION
            "Each table entry represents a configured route
             statement."
             
    INDEX   { cgspInstNetwork,  -- shared index
              cgrtRouteDpc,
              cgrtRouteMask,
              cgrtRouteDestLsCost,
              cgrtRouteDestLinkset
    }
    ::= { cgrtRouteTable  1 }

CgrtRouteEntry  ::= SEQUENCE {
    cgrtRouteDpc                      CItpTcPointCode,
    cgrtRouteMask                     Unsigned32,
    cgrtRouteDestLsCost               Unsigned32,
    cgrtRouteDestLinkset              CItpTcLinksetId,
    cgrtRouteQos                      CItpTcQos,
    cgrtRouteStatus                   INTEGER,
    cgrtRouteMgmtStatus               INTEGER,
    cgrtRouteDynamic                  TruthValue,
    cgrtRouteType                     INTEGER,
    cgrtRouteAdminStatus              INTEGER,
    cgrtRouteRowStatus                RowStatus
}


cgrtRouteDpc                      OBJECT-TYPE
    SYNTAX                        CItpTcPointCode 
    MAX-ACCESS                    not-accessible
    STATUS                        current
    DESCRIPTION
            "The destination point code."
    ::= { cgrtRouteEntry  1 }

cgrtRouteMask                     OBJECT-TYPE
    SYNTAX                        Unsigned32 (0..16777215)
    MAX-ACCESS                    not-accessible
    STATUS                        current
    DESCRIPTION
            "The mask used to define which part of
            cgrtRouteDpc is significant when comparing
            the cgrtRouteDpc to the destination code
            point in the packet to be routed."
    ::= { cgrtRouteEntry  2 }
    
cgrtRouteDestLsCost               OBJECT-TYPE
    SYNTAX                        Unsigned32 (1..9)
    MAX-ACCESS                    not-accessible
    STATUS                        current
    DESCRIPTION
            "The cost assigned to this linkset matching this
            route. Higher numbers represent higher cost."
    ::= { cgrtRouteEntry  3 }

cgrtRouteDestLinkset              OBJECT-TYPE
    SYNTAX                        CItpTcLinksetId 
    MAX-ACCESS                    not-accessible
    STATUS                        current
    DESCRIPTION
            "The linkset that the packet is to be forwarded to on
            matching this route."
    ::= { cgrtRouteEntry  4 }

cgrtRouteQos                      OBJECT-TYPE
    SYNTAX                        CItpTcQos
    MAX-ACCESS                    read-create
    STATUS                        current
    DESCRIPTION
            "The quality of service classification to be assigned 
             to the IP packets used to transport the SS7 messages.
             The value to specify for packets
             when they will be transported on SCTP/IP based 
             linkset."  
    ::= { cgrtRouteEntry  5 }
    
cgrtRouteStatus                  OBJECT-TYPE
    SYNTAX                       INTEGER {
                                           unknown(1),
                                           available(2),
                                           restricted(3),
                                           unavailable(4),
                                           deleted(5)
                                 }
    MAX-ACCESS                   read-create
    STATUS                       current
    DESCRIPTION
            "List of the possible route status values.  These values
             are determine using the status of the linkset specified
             in this route and the route management status.
           
                'unknown'     : Status can not be determined.
                'available'   : Route is available.
                'restricted'  : Traffic is restricted on route.
                'unavailable' : Route is unable to service traffic.
                'deleted'     : Route has been removed."
                
    ::= { cgrtRouteEntry  6 }
    
cgrtRouteMgmtStatus              OBJECT-TYPE
    SYNTAX                       INTEGER {
                                           unknown(1),
                                           allowed(2),
                                           restricted(3),
                                           prohibited(4),
                                           deleted(5)
                                 }
    MAX-ACCESS                   read-create
    STATUS                       current
    DESCRIPTION
        "List of the possible route management route status 
         values.  Route management status are received in 
         transfer-allowed(TFA), transfer-prohibited(TFP), 
         transfer-restricted(TFR), transfer-cluster-allowed(TCA),
         transfer-cluster-prohibited(TCP) and
         transfer-cluster-restricted(TFR) management messages.
            'unknown'     : Status can not be determined.
            'allowed'     : traffic is allowed.
            'restricted'  : Traffic is restricted on route.
            'prohibited'  : Route is prohibited from providing
                            traffic.
            'deleted'     : Route has been removed."
    ::= { cgrtRouteEntry  7 }
        
cgrtRouteDynamic                 OBJECT-TYPE
     SYNTAX                      TruthValue
     MAX-ACCESS                  read-only
     STATUS                      current
     DESCRIPTION          
            "Routes are either static or dynamic.  Static routes 
             are created based on configuration information specified
             by an administrator.  Dynamic routes are created as a
             by product of an network event in certain situations.
             Dynamic routes are only created when summary routing  
             has been activated.  
             
             This object indicates whether this route entry is 
             dynamic or static.
               'true'  - dynamic route
               'false' - static route"
    ::= { cgrtRouteEntry  8 }
    
cgrtRouteType                    OBJECT-TYPE
    SYNTAX                       INTEGER {
                                           unknown(0),
                                           static(1),
                                           cluster(2),
                                           summary(3),
                                           xlist(4),
                                           shadow(5),
                                           management(6),
                                           alias(7) 
                                 }
    MAX-ACCESS                   read-only
    STATUS                       current
    DESCRIPTION
       " When summary or cluster routes are specified this field 
         will provide additional information about the fully 
         qualified routes within the specified clusters.  Since, 
         summary or cluster routes represent a group of 
         destinations it is necessary to collect and maintain 
         status information on routes that are not available.  
         Additional, route statements are created dynamically 
         whenever a TFP or TFR is received on a fully qualified 
         route represented by a defined summary route.  There are 
         three four types of dynamic route as follows.
         List of the possible route status values.
         
         'unknown': Undefined type of route.
         
         'static': A fully-qualified route configured by system
             administrator.
             
         'cluster': An ANSI cluster route.  A DPC and mask
             with length of 16 bits configured by system 
             administrator.
         
         'summary': An DPC and a mask with length 0-10 for ITU and
             0-15,17-23 for ANSI. A summary route is configured by
             a system administrator. 
             
               
         'xlist':  This route is dynamic and is create whenever TFP
             or TFR is received for a point-code represented by a 
             ANSI cluster route.  
             
         'shadow': When a TFP or TFR is received for a point-code 
             represented by a summary or cluster route all route
             statements specified for the summary or cluster 
             destination are copied.  These new routes appear
             under the specific fully-qualified destination.  
             The route will be marked as a shadow when a TFP or
             TFR has not been received for that particular route.
             
         'management' : When a TFP or TFR is received for a 
             point-code represented by a summary route all route 
             statements specified for the summary destination are 
             copied.  The new routes appear under the 
             fully-qualified destination specified in the TFR or 
             TFP.  The route specified in the TFR or TFP will be 
             marked as a dynamic to indicate that MTP3 route 
             management information is available for this route.
             
         'alias': Route statement is created in response
             to conversion statements defined to alias point-codes
             across networks."
    ::= { cgrtRouteEntry  9 }


cgrtRouteAdminStatus             OBJECT-TYPE
    SYNTAX                       INTEGER {
                                           none(0),
                                           unknown(1),
                                           available(2),
                                           restricted(3),
                                           unavailable(4),
                                           deleted(5)
                                 }
    MAX-ACCESS                   read-create
    STATUS                       current
    DESCRIPTION
            "List of the possible administration route status 
             values.
                'none'        : none.
                'unknown'     : Status can not be determined.
                'available'   : Route is available.
                'restricted'  : Traffic is restricted on route.
                'unavailable' : Route is unable to service traffic.
                'deleted'     : Route has been removed.
             
              When the cgrtRouteAdminStatus object is set to the 
              none value the cgrtRouteStatus status will be based 
              on the cgrtRouteMgmtStatus and linkset availability.
              Otherwise the cgrtRouteStatus will be set to the
              value specified in cgrtRouteAdminStatus object."
     DEFVAL { none }
    ::= { cgrtRouteEntry  10 }
    
cgrtRouteRowStatus                OBJECT-TYPE
    SYNTAX                        RowStatus
    MAX-ACCESS                    read-create
    STATUS                        current
    DESCRIPTION
        "The object is used by a management station to create, 
         modify or delete the row entry in cgspPointCodeTable 
         following the RowStatus textual convention.  The only
         object available for modification is the 
         cgrtRouteAdminStatus object."
    ::= { cgrtRouteEntry  11 }
    

-- *************************************************************
-- *                                                           *
-- * Notifications Information                                 *
-- *                                                           *
-- *************************************************************
cgrtNotificationsInfo  OBJECT IDENTIFIER ::= { cgrtObjects 4 }
    
cgrtDestNotifSupFlag        OBJECT-TYPE
     SYNTAX                 TruthValue
     MAX-ACCESS             accessible-for-notify
     STATUS                 current
     DESCRIPTION          
         "A flag to indicate whether destination notifications  
          notifications have been suppressed in the current time 
          interval specified by the cgrtDestNotifWindowTime 
          object.
          
        'true'  Indicates that the device has suppressed the sending 
                of ciscoGrtDestStateChange notifications for the 
                remainder of the time interval. 
              
        'false' Indicates that the device has not suppressed the 
                sending of ciscoGrtDestStateChange notifications in 
                the current time interval." 
    ::= { cgrtNotificationsInfo 1 }
    
cgrtDestNotifChanges        OBJECT-TYPE
     SYNTAX                 OCTET STRING (SIZE(0..255))
     MAX-ACCESS             accessible-for-notify
     STATUS                 current
     DESCRIPTION
        "This object contains a list of destination state changes 
         accumulated until the list is full or the time time interval
         specified in cgrtDestNotifDelayTime has passed.
         
         It consists of one or more tuples packed
         together in the format of '<tuple1><tuple2>...<tuple15>'.
         Each tuple consist of 36 octets in the following format.

         '<cgspInstNetwork>          20 octets null padded
          <cgrtRouteDpc>              4 octets
          <cgrtRouteMask>             4 octets
          <cgrtDestStatus>            4 octets
          <cgrtDestCongestion>        4 octets    
          
         The cgrtRouteDpc, cgrtRouteMask cgrtDestStatus,
         cgrtDestCongestion and cgrtDestAdminState
         are encoded in network byte order.
               
         The maximum number of tuples is 7."
         
    REFERENCE
            "ITU Q752 Table 4 Item 9 - Unavailablity of routeset
             to particulare destination and Telcordia 
             GR-3053-CORE R5-127 SS7 Route Set Remote Congestion"
    ::= { cgrtNotificationsInfo 2 }
    
cgrtMgmtNotifSupFlag        OBJECT-TYPE
     SYNTAX                 TruthValue
     MAX-ACCESS             accessible-for-notify
     STATUS                 current
     DESCRIPTION          
         "A flag to indicate whether management route notifications  
          have been suppressed in the current time interval specified
          by the cgrtMgmtNotifWindowTime object.
          
        'true'  Indicates that the device has suppressed the sending 
                of ciscoGrtDestStateChange notifications for the 
                remainder of the time interval. 
              
        'false' Indicates that the device has not suppressed the 
                sending of ciscoGrtMgmtStateChange notifications in 
                the current time interval." 
    ::= { cgrtNotificationsInfo 3 }
    
cgrtMgmtNotifChanges        OBJECT-TYPE
     SYNTAX                 OCTET STRING (SIZE(0..255))
     MAX-ACCESS             accessible-for-notify
     STATUS                 current
     DESCRIPTION
        "This object contains a list of management route
         state changes accumulated until the list is full or 
         the time time interval specified in 
         cgrtMgmtNotifDelayTime has passed.
         
         It consists of one or more tuples packed
         together in the format of '<tuple1><tuple2>...<tuple6>'.
         Each tuple consist of 68 octets in the following format.

         '<cgspInstNetwork>          20 octets null padded
          <cgrtRouteDpc>              4 octets
          <cgrtRouteMask>             4 octets
          <cgrtRouteDestLsCost>       4 octets
          <cgrtRouteDestLinkset>     20 octets null padded
          <cgrtRouteStatus>           4 octets
          <cgrtRouteMgmtStatus>       4 octets
          <cgrtRouteDynamic>          4 octets
          <cgrtRouteAdminStatus>      4 octets'   
                                     
         The cgrtRouteDpc, cgrtRouteMask,  cgrtRouteDestLsCost,
         cgrtRouteStatus, cgrtRouteMgmtStatus, cgrtRouteDynamic
         and cgrtRouteAdminStatus are encoded in network byte order.
         
         The maximum number of tuples is 3."
         
    ::= { cgrtNotificationsInfo 4 }
    
-- *************************************************************
-- *                                                           *
-- * Notifications                                             *
-- *                                                           *
-- *************************************************************
ciscoGrtDestStateChange NOTIFICATION-TYPE
     OBJECTS {
              cgspEventSequenceNumber,
              cgspCLLICode,
              cgrtDestNotifSupFlag,
              cgrtDestNotifChanges
     }
     STATUS  current
     DESCRIPTION
             "This notification is generated whenever one or more
              destination changes states. This notification 
              contains a list of destination state changes in the
              cgrtDestNotifChanges object.  State changes are
              accumulated until the cgrtDestNotifChanges is 
              full or the maximum delay time is reached.  The delay
              time is specified by the cgrtDestNotifDelayTime 
              object.
              
              It may be necessary to suppress the sending of 
              notification when a large number destinations change 
              state, due the failure of some common resource.  The 
              number of notifications can be controlled by 
              specifying values for cgrtDestNotifWindowTime 
              and cgrtDestNotifMaxPerWindow objects.  When the 
              number of destination state changes exceed the 
              specified value the last notification will indicate 
              that notifications are suppressed for the remainder
              of the window."
     ::= { ciscoGrtNotifications 1 }
     
ciscoGrtMgmtStateChange NOTIFICATION-TYPE
     OBJECTS {
              cgspEventSequenceNumber,
              cgspCLLICode,
              cgrtMgmtNotifSupFlag,
              cgrtMgmtNotifChanges
     }
     STATUS  current 
     DESCRIPTION
             "This notification is generated whenever one or more
              management routes change state.  This notification
              contains a list of management route state changes 
              in the cgrtMgmtNotifChanges object.  State changes 
              are accumulated until the cgrtMgmtNotifChanges
              is full or the maximum delay time is reached.  The 
              delay time is specified by the 
              cgrtMgmtNotifDelayTime object.
              
              It may be necessary to suppress the sending of 
              notification when a large number of routes change 
              state, due the failure of some common resource.
              The number of notifications can be controlled by 
              specifying values for cgrtMgmtNotifWindowTime 
              and cgrtMgmtNotifMaxPerWindow objects.  When the 
              number of route state changes exceed the specified
              value the last notification will indicate that
              notifications are suppressed for the remainder
              of the window."
     ::= { ciscoGrtNotifications 2 }
     
ciscoGrtRouteTableLoad NOTIFICATION-TYPE
     OBJECTS {
              cgspEventSequenceNumber,
              cgspCLLICode,
              cgrtInstLoadStatus,
              cgrtInstTableName,
              cgrtInstLastURL
     }
     STATUS  current 
     DESCRIPTION
             "This notification is generated whenever a load 
              operation is started or completed.  Route table
              configurations can be loaded by CLI requests. 
              In addition, route tables can loaded using
              configuration statements.  This allows route
              tables to be reloaded whenever a device restarts."
     ::= { ciscoGrtNotifications 3 }
           
-- *************************************************************
-- *                                                           *
-- * Conformance Information                                   *
-- *                                                           *
-- *************************************************************
ciscoGrtMIBCompliances OBJECT IDENTIFIER ::= { ciscoGrtMIBConform 1 }
ciscoGrtMIBGroups      OBJECT IDENTIFIER ::= { ciscoGrtMIBConform 2 }

-- Compliance
ciscoGrtMIBCompliance MODULE-COMPLIANCE
    STATUS current
    DESCRIPTION
            "The compliance statement for entities which implement
             the Cisco CISCO-ITP-GRT-MIB.my MIB"
    MODULE -- this module
            MANDATORY-GROUPS {
                    ciscoGrtInstGroup,
                    ciscoGrtDestGroup,
                    ciscoGrtRouteGroup, 
                    ciscoGrtNotificationsGroup
            }
            
         OBJECT           cgrtRouteQos
         MIN-ACCESS       read-only
         DESCRIPTION      "Create/Write access is not required."
         
         OBJECT           cgrtRouteStatus
         MIN-ACCESS       read-only
         DESCRIPTION      "Create/Write access is not required."
         
         OBJECT           cgrtRouteMgmtStatus
         MIN-ACCESS       read-only
         DESCRIPTION      "Create/Write access is not required."
         
         OBJECT           cgrtRouteAdminStatus
         MIN-ACCESS       read-only
         DESCRIPTION      "Create/Write access is not required."
         
         OBJECT           cgrtRouteRowStatus
         MIN-ACCESS       read-only
         DESCRIPTION      "Create/Write access is not required."
    ::= { ciscoGrtMIBCompliances 1 }

-- Units of Conformance

ciscoGrtInstGroup OBJECT-GROUP
    OBJECTS {
             cgrtInstLastChanged,
             cgrtInstLastLoadTime,
             cgrtInstLoadStatus,
             cgrtInstTableName,
             cgrtInstLastURL,
             cgrtInstNumberDestinations,
             cgrtInstNumberRoutes,
             cgrtRouteTableLoadNotifEnabled
    }
    STATUS current
    DESCRIPTION
            "SS7 route instance group"
    ::= { ciscoGrtMIBGroups 1 }
    
ciscoGrtDestGroup OBJECT-GROUP
    OBJECTS {
             cgrtDestNotifDelayTime, 
             cgrtDestNotifWindowTime,  
             cgrtDestNotifMaxPerWindow,
             cgrtDestNotifEnabled,
             cgrtDestNotifSupFlag,
             cgrtDestNotifChanges,
             cgrtDestStatus,
             cgrtDestCongestion
    }
    STATUS current
    DESCRIPTION
            "SS7 Destination group "
    ::= { ciscoGrtMIBGroups 2 }
    
ciscoGrtRouteGroup OBJECT-GROUP
    OBJECTS {
             cgrtRouteMaxDynamic,
             cgrtMgmtNotifDelayTime,
             cgrtMgmtNotifWindowTime, 
             cgrtMgmtNotifMaxPerWindow,
             cgrtMgmtNotifEnabled,
             cgrtMgmtNotifSupFlag,
             cgrtMgmtNotifChanges,
             cgrtDynamicRoutes,
             cgrtDynamicRoutesDropped,
             cgrtRouteQos,                      
             cgrtRouteStatus,     
             cgrtRouteMgmtStatus,
             cgrtRouteDynamic,
             cgrtRouteType,
             cgrtRouteAdminStatus,
             cgrtRouteRowStatus
    }
    STATUS current
    DESCRIPTION
            "SS7 Route group "
    ::= { ciscoGrtMIBGroups 3 }
    
    
ciscoGrtNotificationsGroup NOTIFICATION-GROUP
        NOTIFICATIONS {
                ciscoGrtDestStateChange,
                ciscoGrtMgmtStateChange,
                ciscoGrtRouteTableLoad
        }                      
        STATUS current
        DESCRIPTION
                "Gateway route notification objects."
    ::= { ciscoGrtMIBGroups 4 }
END
