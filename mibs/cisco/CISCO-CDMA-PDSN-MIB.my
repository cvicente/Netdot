-- *****************************************************************
-- CISCO-CDMA-PDSN-MIB.my:  CDMA PDSN Management MIB
-- Jan. 2000, Ying He, Christian Pechard, Thamilarasu K, 
--            Kirit B. Joshi, Hong Luo
--
-- Copyright (c) 2000-2003, 2004, 2005 by Cisco Systems, Inc.
-- All rights reserved.
-- 
-- *****************************************************************

CISCO-CDMA-PDSN-MIB DEFINITIONS ::= BEGIN

IMPORTS
         MODULE-IDENTITY,
         NOTIFICATION-TYPE,
         OBJECT-TYPE,
         Unsigned32,
         Counter32,
         Gauge32,
         IpAddress,
         TimeTicks
                 FROM SNMPv2-SMI

         DateAndTime,
         TruthValue,
         TEXTUAL-CONVENTION
              FROM SNMPv2-TC

         MODULE-COMPLIANCE,
         NOTIFICATION-GROUP,
         OBJECT-GROUP
                 FROM SNMPv2-CONF

         SnmpAdminString
                 FROM SNMP-FRAMEWORK-MIB

         ciscoMgmt
                 FROM CISCO-SMI

         ZeroBasedCounter32
                 FROM RMON2-MIB 

         InetAddress,
         InetAddressType
                 FROM INET-ADDRESS-MIB;

  
ciscoCdmaPdsnMIB MODULE-IDENTITY
         LAST-UPDATED    "200502020000Z"
         ORGANIZATION    "Cisco Systems, Inc."
         CONTACT-INFO
                 "        Cisco Systems
                          Customer Service

                 Postal: 170 W Tasman Drive
                          San Jose, CA  95134
                          USA

                    Tel: +1 800 553-NETS

                 E-mail: cdma@cisco.com"

         DESCRIPTION
                 "This MIB is to support the CDMA PDSN (Packet Data Serving
                  Node) feature.  A CDMA2000 network supports wireless data
                  communication through 3G CDMA radio access technology and
                  3G A10/A11 interface.  PDSN acts as a foreign agent that
                  establishes, maintains and terminates the link layer to a
                  mobile station.

                  The high level architecture of a third generation CDMA2000
                  network is shown below:

                       +========+=+            +=========+          +=========+
                       | RAdio  |P|            |         |   Data   |  Home   |
                       | Network|C|==A10/A11==-|  PDSN   |===Core===| Network |
                       |  (RAN) |F| Interface  |         |  Network |         |
                       +========+=+            +=========+   (DCN)  +=========+
                          /|\                 Foreign Agent         Home Agent
                           |                     (FA)                  (HA)
                           |   Visited Access
                           |  Provider Network               
                           |                                 
                          \|/                                
                       +========+
                       | Mobile |
                       | Station|
                       |  (MS)  |
                       +========+

                  The following diagram illustrates protocols usage by the
                  CDMA2000 network elements:

                    MS ===== RAN ======== PDSN ======== DCN ====== Home Network
                    |        |  A10/A11   |                        |
                    |        +=signaling==+                        |
                    |                     |                        |
                    |                     +...L2TP/L2F tunnelling..+
                    |                     |                        |
                    +======== PPP ========+                        |
                    |                     |                        |
                    |                     +..Mobile IP tunnelling..+
                    |                                              |
                    |                                              |
                    |                                              |
                    +=================Mobile IP====================+
                    |                                              |
                    |                                              |
                    +======================data====================+


                  The CDMA PDSN MIB provides operational information for a 
                  CDMA PDSN implementation.  The following areas are managed:

                      1) Global PDSN information.  This area contains generic
                         information such as the number of active/failed
                         sessions, PDSN hostname.

                      2) PDSN session information.  This area contains 
                         details about PPP sessions maintained by the
                         PDSN router and other related information such as
                         flows or PCF. 

                      3) Failure notification.  This area contains details
                         of notifications sent to network management
                         applications in case of session failure.


                  Acronyms and terms:

                    A10/A11         A10 interface is a virtual interface
                    interface       used for transporting data between
                                    the RAN and the PDSN.
  
                                    A11 interface is the signaling
                                    protocol used for maintaining a
                                    logical connection between the RAN
                                    and PDSN.

                    BSID            Base Station Identifier

                    CANID           Current Access Network Identifier
                    
                    CDMA            Code Division Multiple Access

                    CVSE            Customer/Vendor Specific Extension

                    DCN             Data Core Network

                    ESN             Electronic Serial Number

                    FA              Foreign Agent

                    Foreign Agent   A router on a mobile node's visited
                                    network which provides routing
                                    services to the mobile node while
                                    registered.  The foreign agent
                                    delivers datagrams to the mobile
                                    node that were tunneled by the
                                    mobile node's home agent.
                                    For datagrams sent by a mobile node,
                                    the foreign agent may serve as a
                                    default router for registered mobile
                                    nodes.  Refer to RFC 2002 for more
                                    details.

                    GRE             Generic Routing Encapsulation. Refer to
                                    RFC 1701 for more details.

                    HA              Home Agent

                    Home Agent      A router on a mobile node's home
                                    network which tunnels datagrams for
                                    delivery to the mobile node when it
                                    is away from home, and maintains
                                    current location information for the
                                    mobile node.  Refer to RFC 2002 for
                                    more details.

                    IMSI            International Mobile Station Identifier

                    IPCP            Internet Protocol Control Protocol
                    
                    IS              In service

                    IRM             International Roaming MIN

                    LCP             Link Control Protocol

                    MC              Mobile Client

                    MIN             Mobile Identifier Number

                    MN              Mobile Node

                    Mobile Client   A component which can interact with
                                    MoIP entities such as Foreign Agent
                                    and Home Agent.

                    Mobile IP       Protocol enhancements that allow
                                    transparent routing of IP datagrams
                                    to mobile nodes.
                                    Refer to RFC 2002 for more details.

                    Mobile Station/ A host or router that changes its 
                    Mobile Node     point of attachment from one 
                                    network or subnetwork to another.
                                    A mobile node may change its 
                                    location without changing its
                                    IP address.

                    MoIP            Mobile IP

                    MSID            Mobile Station Identifier

                    MS              Mobile Station
                    
                    NAI             Network Access Identifier   
                   
                    OOS             Out of service

                    PANID           Previous Access Network Identifier
                    
                    PCF             Packet Control Function

                    PDSN            Packet Data Serving Node

                    PDSN flow       A conversation between one user
                                    (identified by an IP address) and
                                    a HA using a PDSN session.

                    PDSN session    A PPP connection between a MS and
                                    the PDSN.  One session may contain
                                    one or multiple PDSN flows.

                    PPPoGRE         Point-to-Point over 
                                    Generic Routing Encapsulation

                    PPPoHDLC        Point-to-Point over
                                    High Level Data Link Control

                    Proxy           Mechanism used by PDSN to provide
                    mobile IP       MoIP services to a MS which does
                                    not implement a mobile client. PDSN
                                    will be the proxy MC for the MS.

                    RAN/RN          Radio Network

                    RNPDIT          Radio Network Packet Data 
                                    Inactivity Timer

                    RP              Radio Packet
                    
                    SDB             Short Data Burst

                    Simple IP       IP routing used by a MS when MoIP
                                    services are not needed.

                    SO/So           Service Option.
                                    The Service Option is a parameter 
                                    that specifies the air interface 
                                    between MS and RN for packet 
                                    data service.

                    SPI             Security Parameter Index."

         REVISION        "200502020000Z"
         DESCRIPTION
                  "Added new objects for PCF and Service option based
                   RP and PPP statistics."
         REVISION        "200308260000Z"
         DESCRIPTION
                  "Added new objects for PCF and Service option based
                   RP and PPP statistics."
         REVISION        "200209090000Z"
         DESCRIPTION
                  "Added new objects for PPP re-negotiation counters."
         REVISION        "200202190000Z"
         DESCRIPTION
                  "Added PDSN cluster feature and added/appended the 
                   following groups:
                   Appended cCdmaPerformanceStats group with following:
                       cCdmaServiceOptionStats, cCdmaHandoffStats,
                       cCdmaStatusChangeStats, cCdmaAddressSchemeStats.
                   Appended cCdmaFlowTypeStats with failuure statitics.
                   Appended cCdmaSystemInfo with cCdmaSystemStatus.
                   Added cCdmaConfig group with three subgroups:
                       cCdmaThresholdConfig, cCdmaPdsnCluster and
                       cCdmaNotifConfig."
                   
         REVISION        "200110180000Z"
         DESCRIPTION
                  "Create a new cCdmaPerformanceStats to hold all new performance
                   statistics related counters for PDSN release 1.1 and newer." 
         REVISION        "200104100000Z"
         DESCRIPTION
                  "Syntax for cCdmaSessionServiceOption changed."
         REVISION        "200101220000Z"
         DESCRIPTION
                  "New Objects Definitions for
                   R-P Registration Statistics & Update Statistics
                   were added."
         REVISION        "200003060000Z"
         DESCRIPTION
                 "Initial revision of this MIB module."
         ::= { ciscoMgmt 157 }


CCdmaMsidType ::= TEXTUAL-CONVENTION
         STATUS      current
         DESCRIPTION   
                 "Mobile Station Identifier format type of a mobile 
                  station:

                     - 'imsi' indicates IMSI format (15 digits max)

                     - 'min' indicates MIN format (10 digits max)

                     - 'irm' indicates IRM (10 digits max)

                     - 'other' in other cases"
         REFERENCE
                 "ITU-T, TIA, EIA are international telecommunications
                  organizations.  For more details on:

                     - IMSI refer to ITU-T document E.212 

                     - MIN refer to TIA document TIA/EIA-41-E

                     - IRM refer to TIA document TSB-29"
         SYNTAX      INTEGER {
                     other(1),
                     imsi(2),
                     min(3),
                     irm(4)
                     }

CCdmaSystemStatus ::= TEXTUAL-CONVENTION
         STATUS      current
         DESCRIPTION
                 "PDSN operational status. The valid value are:
                     - 'unknown' indicates status is unknown.

                     - 'up' indicates system is up and providing
                       service.

                     - 'down' indicates system is down and not
                       providing service.

                     - 'testing' indicates system is up, but is in
                       testing state, call can only be made through
                       CLI, not through regular through A11/A10
                       interface.

                     - 'insufficientResources' indicates system is 
                       up and runs out of system resource."
         SYNTAX      INTEGER {
                     unknown(0),
                     up(1),
                     down(2),
                     testing(3),
                     insufficientResources(4)
                     }

CCdmaServiceAffectedLevel ::= TEXTUAL-CONVENTION
         STATUS      current
         DESCRIPTION
                 "CDMA severity level of affected service:
                    - 'warning' indicates something is abnormal, but 
                      service is not affected.
                    - 'minor' indicates service has been slightly 
                      affected.
                    - 'major' indicates service has been severely
                      affected.
                    - 'critical' indicates service can not be provided
                      anymore."
         SYNTAX      INTEGER {
                     warning(1),
                     minor(2),
                     major(3),
                     critical(4)
                     }
                     
CCdmaServiceOption ::= TEXTUAL-CONVENTION
         STATUS      current
         DESCRIPTION
                "A Packet Data Service Option is a parameter that 
                 specifies the air interface between MS and RN 
                 for packet data service."
         SYNTAX      Unsigned32

ciscoCdmaPdsnMIBObjects  OBJECT IDENTIFIER ::= { ciscoCdmaPdsnMIB 1 }
cCdmaSystemInfo          OBJECT IDENTIFIER ::= { ciscoCdmaPdsnMIBObjects 1 }
cCdmaPcfInfo             OBJECT IDENTIFIER ::= { ciscoCdmaPdsnMIBObjects 2 }
cCdmaSessionInfo         OBJECT IDENTIFIER ::= { ciscoCdmaPdsnMIBObjects 3 }
cCdmaFailHistInfo        OBJECT IDENTIFIER ::= { ciscoCdmaPdsnMIBObjects 4 }
cCdmaRPRegistrationStats OBJECT IDENTIFIER 
                            ::= { ciscoCdmaPdsnMIBObjects 5 }
cCdmaRPUpdateStats       OBJECT IDENTIFIER 
                            ::= { ciscoCdmaPdsnMIBObjects 6 }
cCdmaPerformanceStats    OBJECT IDENTIFIER
                            ::= { ciscoCdmaPdsnMIBObjects 7 }
cCdmaConfig              OBJECT IDENTIFIER
                            ::= { ciscoCdmaPdsnMIBObjects 8 }
cCdmaNotifObjects        OBJECT IDENTIFIER
                            ::= { ciscoCdmaPdsnMIBObjects 9 }
cCdmaRpErrors            OBJECT IDENTIFIER
                            ::= { ciscoCdmaPdsnMIBObjects 10 }

-- *********************************************************************
-- RP Error statistics group
-- *********************************************************************
cCdmaRPRegReqErrors       OBJECT IDENTIFIER
                            ::= { cCdmaRpErrors 1 }
cCdmaRPRegUpdAckErrors    OBJECT IDENTIFIER
                            ::= { cCdmaRpErrors 2 }
cCdmaRPSessUpdAckErrors   OBJECT IDENTIFIER
                            ::= { cCdmaRpErrors 3 }
cCdmaRPRegReplyErrors     OBJECT IDENTIFIER
                            ::= { cCdmaRpErrors 4 }
cCdmaRPRegUpdErrors       OBJECT IDENTIFIER
                            ::= { cCdmaRpErrors 5 }
cCdmaRPSessUpdErrors      OBJECT IDENTIFIER
                            ::= { cCdmaRpErrors 6 }

-- *********************************************************************
-- Performance statistics group for PDSN R1.1
-- *********************************************************************

cCdmaRpRegStats          OBJECT IDENTIFIER
                            ::= { cCdmaPerformanceStats 1 }
cCdmaRpUpdStats          OBJECT IDENTIFIER
                            ::= { cCdmaPerformanceStats 2 }
cCdmaPppStats            OBJECT IDENTIFIER
                            ::= { cCdmaPerformanceStats 3 }
cCdmaTrafficStats        OBJECT IDENTIFIER
                            ::= { cCdmaPerformanceStats 4 }
cCdmaFlowTypeStats       OBJECT IDENTIFIER
                            ::= { cCdmaPerformanceStats 5 }
cCdmaServiceOptionStats  OBJECT IDENTIFIER
                            ::= { cCdmaPerformanceStats 6 }

cCdmaHandoffStats        OBJECT IDENTIFIER
                            ::= { cCdmaPerformanceStats 7 }

cCdmaStatusChangeStats   OBJECT IDENTIFIER
                            ::= { cCdmaPerformanceStats 8 }

cCdmaAddressSchemeStats  OBJECT IDENTIFIER
                            ::= { cCdmaPerformanceStats 9 }

cCdmaPcfSoRpRegStats     OBJECT IDENTIFIER
                            ::= { cCdmaPerformanceStats 10 }

cCdmaPcfSoRpUpdStats     OBJECT IDENTIFIER 
                            ::= { cCdmaPerformanceStats 11 }

cCdmaPcfSoPppSetupStats  OBJECT IDENTIFIER 
                            ::= { cCdmaPerformanceStats 12 }

cCdmaRpSessUpdStats      OBJECT IDENTIFIER
                            ::= { cCdmaPerformanceStats 13 }

cCdmaPcfSoRpSessUpdStats OBJECT IDENTIFIER 
                            ::= { cCdmaPerformanceStats 14 }

-- ******************************************************************
-- PDSN configuration:
-- ******************************************************************

cCdmaThresholdConfig OBJECT IDENTIFIER
                            ::= { cCdmaConfig 1 }

cCdmaPdsnCluster     OBJECT IDENTIFIER
                            ::= { cCdmaConfig 2 }

cCdmaNotifConfig      OBJECT IDENTIFIER
                            ::= { cCdmaConfig 3 }

-- *******************************************************************
-- PDSN cluster 
-- *******************************************************************

cCdmaClusterCommon OBJECT IDENTIFIER
         ::= { cCdmaPdsnCluster 1 }

cCdmaClusterMemberInfo OBJECT IDENTIFIER
         ::= { cCdmaPdsnCluster 2 }

cCdmaClusterControllerInfo OBJECT IDENTIFIER
         ::= { cCdmaPdsnCluster 3 }


-- ******************************************************************
-- * CDMA PDSN system information
-- ******************************************************************

cCdmaSessionTotal   OBJECT-TYPE
         SYNTAX      Gauge32
         MAX-ACCESS  read-only
         STATUS      current
         DESCRIPTION
                 "The total number of sessions currently established with
                  this system." 
         ::= { cCdmaSystemInfo 1 }

cCdmaSessionMaxAllowed OBJECT-TYPE
         SYNTAX      Unsigned32
         MAX-ACCESS  read-only
         STATUS      current
         DESCRIPTION
                 "The maximum number of sessions allowed by this system."
         ::= { cCdmaSystemInfo 2 }

cCdmaPcfTotal       OBJECT-TYPE
         SYNTAX      Gauge32
         MAX-ACCESS  read-only
         STATUS      current
         DESCRIPTION
                 "The total number of PCF currently interacting with this
                  system."
         ::= { cCdmaSystemInfo 3 }

cCdmaPcfMaxAllowed  OBJECT-TYPE
         SYNTAX      Unsigned32
         MAX-ACCESS  read-write
         STATUS      current
         DESCRIPTION
                 "The maximum number of PCF allowed by this system."
         ::= { cCdmaSystemInfo 4 }  

cCdmaSimpleIpFlowTotal OBJECT-TYPE
         SYNTAX      Gauge32
         MAX-ACCESS  read-only
         STATUS      current
         DESCRIPTION
                 "The total number of flows currently using simple IP service."
         ::= { cCdmaSystemInfo 5}
  
cCdmaMobileIpFlowTotal OBJECT-TYPE
         SYNTAX      Gauge32
         MAX-ACCESS  read-only
         STATUS      current
         DESCRIPTION
                 "The total number of flows currently using MoIP services."
         ::= { cCdmaSystemInfo 6 }

cCdmaProxyMobileIpFlowTotal OBJECT-TYPE
         SYNTAX      Gauge32
         MAX-ACCESS  read-only
         STATUS      current
         DESCRIPTION
                 "The total number of flows currently using proxy MoIP service."
         ::= { cCdmaSystemInfo 7 }

cCdmaSessionFailTotal OBJECT-TYPE
         SYNTAX      ZeroBasedCounter32
         MAX-ACCESS  read-only
         STATUS      current
         DESCRIPTION
                 "The number of A10/A11 session failures occurring since
                  PDSN agent restarted.  sysUpTime can be polled to 
                  determine if the agent has been restarted."
         REFERENCE
                 "Refer to TIA/EIA international telecommunications 
                  organization standard TR 45.4 for details about 
                  A10/A11 interface."
         ::= { cCdmaSystemInfo 8 }

cCdmaServingPdsnHostname OBJECT-TYPE
         SYNTAX      SnmpAdminString (SIZE(0..32))
         MAX-ACCESS  read-only
         STATUS      current
         DESCRIPTION
                 "Hostname of the serving PDSN."
         ::= { cCdmaSystemInfo 9 }

cCdmaSessionPdsnAuthenTimer OBJECT-TYPE
         SYNTAX      TimeTicks
         MAX-ACCESS  read-write
         STATUS      current
         DESCRIPTION
                 "Timer (measured in hundredths of a second) for MoIP
                  users not using PPP authentication.  After PPP session
                  establishment, the session will be terminated if the 
                  MoIP user is not authenticated via MoIP for a period 
                  longer than this timer."
         ::= { cCdmaSystemInfo 10 }

cCdmaSessionPdsnMaxFailHistory OBJECT-TYPE
         SYNTAX      Unsigned32 (0..2000)
         MAX-ACCESS  read-write
         STATUS      current
         DESCRIPTION
                 "Maximum number of entries in the user failure information
                  table."
         DEFVAL      { 100 }
         ::= { cCdmaSystemInfo 11 }

cCdmaSessionMaxNotifEnabled OBJECT-TYPE
         SYNTAX      TruthValue
         MAX-ACCESS  read-write
         STATUS      current
         DESCRIPTION
                 "'true' indicates failure notification will be sent out
                  when the maximum number of sessions has been reached."
         DEFVAL      { false }
         ::= { cCdmaSystemInfo 12 }

cCdmaPcfMaxAllowedNotifEnabled OBJECT-TYPE
         SYNTAX      TruthValue
         MAX-ACCESS  read-write
         STATUS      current
         DESCRIPTION
                 "'true' indicates failure notification will be sent out
                   when the maximum number of interconnected PCF has 
                   been reached."
         DEFVAL      { false }
         ::= { cCdmaSystemInfo 13 }

cCdmaFormatErrorNotifEnabled OBJECT-TYPE
         SYNTAX      TruthValue
         MAX-ACCESS  read-write
         STATUS      obsolete
         DESCRIPTION
                 "'true' indicates failure notification will be sent 
                  out when invalid arguments are received from PCF 
                  leading to session termination."
         DEFVAL      { false }
         ::= { cCdmaSystemInfo 14 }

cCdmaRegReqFailedNotifEnabled OBJECT-TYPE
         SYNTAX      TruthValue
         MAX-ACCESS  read-write
         STATUS      current
         DESCRIPTION
                 "'true' indicates failure notification will be sent out
                  when registration request fails termination."
         DEFVAL      { false }
         ::= { cCdmaSystemInfo 15 }

cCdmaSystemVersion OBJECT-TYPE
         SYNTAX  SnmpAdminString
         MAX-ACCESS  read-only
         STATUS  current
         DESCRIPTION
             "CISCO PDSN Release Version, example output: 1.1."
         ::= { cCdmaSystemInfo 16 }

cCdmaSystemStatus  OBJECT-TYPE
         SYNTAX  CCdmaSystemStatus
         MAX-ACCESS  read-only
         STATUS  current
         DESCRIPTION
                 "PDSN subsystem operational status."
         ::= { cCdmaSystemInfo 17 }
         
cCdmaActiveSessions OBJECT-TYPE
         SYNTAX  Gauge32
         MAX-ACCESS  read-only
         STATUS  current
         DESCRIPTION
                 "The total number of sessions in active state."
         ::= { cCdmaSystemInfo 18 }
         
cCdmaDormantSessions OBJECT-TYPE
         SYNTAX  Gauge32
         MAX-ACCESS  read-only
         STATUS  current
         DESCRIPTION
                 "The total number of sessions in dormant state."
         ::= { cCdmaSystemInfo 19 }

cCdmaSrEnabled  OBJECT-TYPE
         SYNTAX  TruthValue
         MAX-ACCESS  read-only
         STATUS  current
         DESCRIPTION
                 "An indication of whether session redundancy feature
                  is enabled."
         ::= { cCdmaSystemInfo 20 }

cCdmaPPPoGRESessionTotal   OBJECT-TYPE
         SYNTAX      Gauge32
         MAX-ACCESS  read-only
         STATUS      current
         DESCRIPTION
                 "The total number of PPPoGRE sessions currently
                  established with this system." 
         ::= { cCdmaSystemInfo 21 }

cCdmaHDLCoGRESessionTotal   OBJECT-TYPE
         SYNTAX      Gauge32
         MAX-ACCESS  read-only
         STATUS      current
         DESCRIPTION
                 "The total number of HDLCoGRE sessions currently
                  established with this system." 
         ::= { cCdmaSystemInfo 22 }

cCdmaEstablishedSessions   OBJECT-TYPE
         SYNTAX      ZeroBasedCounter32
         MAX-ACCESS  read-only
         STATUS      current
         DESCRIPTION
                 "The total number of sessions established 
                  since system was last restarted" 
         ::= { cCdmaSystemInfo 23 }

cCdmaReleasedSessions   OBJECT-TYPE
         SYNTAX      ZeroBasedCounter32
         MAX-ACCESS  read-only
         STATUS      current
         DESCRIPTION
                 "The total number of sessions released 
                  since system was last restarted" 
         ::= { cCdmaSystemInfo 24 }

cCdmaMSIDFlowTotal OBJECT-TYPE
         SYNTAX      Gauge32
         MAX-ACCESS  read-only
         STATUS      current
         DESCRIPTION
                 "The total number of flows currently using 
                  MSID service."
         ::= { cCdmaSystemInfo 25 }

cCdmaVPDNFlowTotal OBJECT-TYPE
         SYNTAX      Gauge32
         MAX-ACCESS  read-only
         STATUS      current
         DESCRIPTION
                 "The total number of flows currently using 
                  VPDN service."
         ::= { cCdmaSystemInfo 26 }

-- ******************************************************************
-- * CDMA PDSN PCF table
-- ******************************************************************
  
cCdmaPcfTable       OBJECT-TYPE
         SYNTAX      SEQUENCE OF CCdmaPcfEntry
         MAX-ACCESS  not-accessible
         STATUS      current
         DESCRIPTION
                 "PDSN PCF table.  Contains the reference about PCF in 
                  the RAN currently interacting with the PDSN.  An entry
                  is created for every session opened by a PCF not 
                  recorded in this table.  An entry is deleted when all
                  session initiated by a PCF are dismantled."
         ::= { cCdmaPcfInfo 1 }
  
cCdmaPcfEntry   OBJECT-TYPE
         SYNTAX      CCdmaPcfEntry
         MAX-ACCESS  not-accessible
         STATUS      current
         DESCRIPTION
                 "A conceptual row in the PCF table."
         INDEX { cCdmaPcfIpAddress }
         ::= { cCdmaPcfTable 1 }
  
CCdmaPcfEntry ::=
         SEQUENCE {
             cCdmaPcfIpAddress                   IpAddress,
             cCdmaPcfSessionTotal                Gauge32,
             cCdmaPcfSessionMaxTotal             Gauge32,
             cCdmaPcfErrorTotal                  Gauge32
         }
  
cCdmaPcfIpAddress   OBJECT-TYPE
         SYNTAX      IpAddress
         MAX-ACCESS  not-accessible 
         STATUS      current
         DESCRIPTION   
                 "IP address identifying a PCF."
         ::= { cCdmaPcfEntry 1 }

cCdmaPcfSessionTotal OBJECT-TYPE
         SYNTAX      Gauge32
         MAX-ACCESS  read-only 
         STATUS      current
         DESCRIPTION   
                 "Total number of sessions currently established with a 
                  PCF."
         ::= { cCdmaPcfEntry 2 }

cCdmaPcfSessionMaxTotal OBJECT-TYPE
         SYNTAX      Gauge32
         MAX-ACCESS  read-only 
         STATUS      current
         DESCRIPTION   
                 "Historical maximum number of connections that were
                  simultaneously established for a PCF."
         ::= { cCdmaPcfEntry 3 }

cCdmaPcfErrorTotal OBJECT-TYPE
         SYNTAX      Gauge32
         MAX-ACCESS  read-only 
         STATUS      current
         DESCRIPTION   
                 "Total number of session errors for a PCF."
         ::= { cCdmaPcfEntry 4 }

-- ******************************************************************
-- * CDMA PDSN session table
-- ******************************************************************
  
cCdmaSessionTable   OBJECT-TYPE
         SYNTAX      SEQUENCE OF CCdmaSessionEntry
         MAX-ACCESS  not-accessible
         STATUS      obsolete
         DESCRIPTION
                 "PDSN Session table.  Contains the parameters
                  and statistics related to a session.  An entry is created
                  for every PPP connection opened by a PCF.  An entry is deleted
                  when the session is dismantled, either by PDSN or PCF."
         ::= { cCdmaSessionInfo 1 }
  
cCdmaSessionEntry   OBJECT-TYPE
         SYNTAX      CCdmaSessionEntry
         MAX-ACCESS  not-accessible
         STATUS      obsolete
         DESCRIPTION
                 "A conceptual row in the PDSN session table."
         INDEX { cCdmaSessionMsid }
         ::= { cCdmaSessionTable 1 }
  
CCdmaSessionEntry ::=
         SEQUENCE {
             cCdmaSessionMsid                    OCTET STRING,
             cCdmaSessionMsidType                CCdmaMsidType,
             cCdmaSessionEsn                     OCTET STRING,
             cCdmaSessionPdsnIp                  IpAddress,
             cCdmaSessionFaIp                    IpAddress,
             cCdmaSessionA11HaIp                 IpAddress,
             cCdmaSessionA11FaIp                 IpAddress,
             cCdmaSessionKey                     OCTET STRING,
             cCdmaSessionConnId                  OCTET STRING,
             cCdmaSessionMoMtInd                 INTEGER,
             cCdmaSessionPppCompressEnabled      TruthValue,
             cCdmaSessionVJCompressEnabled       TruthValue,
             cCdmaSessionServiceOption           Unsigned32,
             cCdmaSessionSentOctets              ZeroBasedCounter32,
             cCdmaSessionRcvdOctets              ZeroBasedCounter32,
             cCdmaSessionSentPkts                ZeroBasedCounter32,
             cCdmaSessionRcvdPkts                ZeroBasedCounter32,
             cCdmaSessionDiscardedOutPkts        ZeroBasedCounter32,
             cCdmaSessionDiscardedInPkts         ZeroBasedCounter32,
             cCdmaSessionConnStartTime           DateAndTime,
             cCdmaActiveConnTime                 Unsigned32,         
             cCdmaSessionFlowCount               Gauge32,
             cCdmaSessionStatus                  INTEGER,
             cCdmaSessionRegLifeTime             TimeTicks,
             cCdmaSessionRegTimeToExpire         TimeTicks,
             cCdmaSessionGREFromIPPkts           ZeroBasedCounter32,
             cCdmaSessionGREToIPPkts             ZeroBasedCounter32
         }

cCdmaSessionMsid    OBJECT-TYPE
         SYNTAX      OCTET STRING (SIZE(5..15))
         MAX-ACCESS  not-accessible 
         STATUS      obsolete
         DESCRIPTION   
                 "Mobile Station Identifier (MSID) of a MS."
         REFERENCE
                 "For more details on MSID refer to international  
                  telecommunications organization TIA document TR-45.5, IS-2000"
         ::= { cCdmaSessionEntry 1 }

cCdmaSessionMsidType OBJECT-TYPE
         SYNTAX      CCdmaMsidType
         MAX-ACCESS  read-only 
         STATUS      obsolete
         DESCRIPTION   
                 "Mobile Station Identifier (MSID) format type of a mobile 
                  station.  Valid choices are:

                     - 'imsi' indicates IMSI format (15 digits max)

                     - 'min' indicates MIN format (10 digits max)

                     - 'irm' indicates IRM (10 digits max)

                     - 'other' in other cases"
         ::= { cCdmaSessionEntry 2 }

cCdmaSessionEsn     OBJECT-TYPE
         SYNTAX      OCTET STRING (SIZE(4))
         MAX-ACCESS  read-only
         STATUS      obsolete
         DESCRIPTION   
                 "Electronic serial number of a MS."
         REFERENCE
                 "TIA, EIA are international telecommunications 
                  organizations.  For more details on ESN refer to 
                  TIA/EIA document TR-45.5, IS-2000."
         ::= { cCdmaSessionEntry 3 }

cCdmaSessionPdsnIp  OBJECT-TYPE
         SYNTAX      IpAddress
         MAX-ACCESS  read-only
         STATUS      obsolete
         DESCRIPTION   
                 "Serving PDSN IP address."
         ::= { cCdmaSessionEntry 4 }             

cCdmaSessionFaIp    OBJECT-TYPE
         SYNTAX      IpAddress
         MAX-ACCESS  read-only
         STATUS      obsolete
         DESCRIPTION   
                 "PDSN IP address serving as Foreign Agent to the MS."
         ::= { cCdmaSessionEntry 5 } 

cCdmaSessionA11HaIp OBJECT-TYPE
         SYNTAX      IpAddress
         MAX-ACCESS  read-only
         STATUS      obsolete
         DESCRIPTION   
                 "MoIP Home Agent address on the A11 interface.
                 (This is nothing but PDSN IP Address)"
         REFERENCE
                 "Refer to TIA/EIA international telecommunications 
                  organization standard TR 45.4 for details about 
                  A10/A11 interface."
         ::= { cCdmaSessionEntry 6  }       

cCdmaSessionA11FaIp OBJECT-TYPE
         SYNTAX      IpAddress
         MAX-ACCESS  read-only
         STATUS      obsolete
         DESCRIPTION   
                 "MoIP Foreign Agent address on the A11 interface.
                 (This is nothing but PCF IP Address)"
         REFERENCE
                 "Refer to TIA/EIA international telecommunications 
                  organization standard TR 45.4 for details about 
                  A10/A11 interface."
         ::= { cCdmaSessionEntry 7  }            

cCdmaSessionKey     OBJECT-TYPE
         SYNTAX      OCTET STRING (SIZE(4))
         MAX-ACCESS  read-only 
         STATUS      obsolete
         DESCRIPTION   
                 "Session identification key used by GRE protocol."
         REFERENCE
                 "Refer to RFC 1701 for more details."
         ::= { cCdmaSessionEntry 8 }

cCdmaSessionConnId  OBJECT-TYPE
         SYNTAX      OCTET STRING (SIZE(4))
         MAX-ACCESS  read-only
         STATUS      obsolete
         DESCRIPTION
                 "Connection ID of the IP/GRE session.  Consists of 4 
                  octets locally unique within a PDSN session."
         ::= { cCdmaSessionEntry 9 }

cCdmaSessionMoMtInd OBJECT-TYPE
         SYNTAX      INTEGER {
                       other(1),
                       mobileOriginated(2),
                       mobileTerminated(3)
                     }
         MAX-ACCESS  read-only
         STATUS      obsolete
         DESCRIPTION 
                 "Mobile Originated/Mobile Terminated Indicator.

                    - mobileOriginated, MS initiated the session

                    - mobileTerminated, PDSN initiated the session"
         ::= { cCdmaSessionEntry 10 }

cCdmaSessionPppCompressEnabled OBJECT-TYPE
         SYNTAX      TruthValue
         MAX-ACCESS  read-only
         STATUS      obsolete
         DESCRIPTION 
                 "'true' indicates compression of PPP is enabled."
         ::= { cCdmaSessionEntry 11 }
             
cCdmaSessionVJCompressEnabled OBJECT-TYPE
         SYNTAX      TruthValue
         MAX-ACCESS  read-only
         STATUS      obsolete
         DESCRIPTION 
                 "'true' indicates Van-Jacobson compression of TCP/IP 
                  header is enabled."
         ::= { cCdmaSessionEntry 12 }

cCdmaSessionServiceOption OBJECT-TYPE
         SYNTAX      Unsigned32
         MAX-ACCESS  read-only
         STATUS      obsolete
         DESCRIPTION   
                 "Defines type of data service and rate set utilized."
         REFERENCE
                 "TIA, EIA are international telecommunications 
                  organizations.  For more details on the type of data 
                  and rate set utilized refer to EIA/TIA document 
                  TSB 58-B."
         ::= { cCdmaSessionEntry 13 }            

cCdmaSessionSentOctets OBJECT-TYPE
         SYNTAX      ZeroBasedCounter32
         MAX-ACCESS  read-only
         STATUS      obsolete
         DESCRIPTION      
                 "The number of data octets sent to the mobile user
                  since session established."
         REFERENCE
                 "Refer to TIA/EIA international telecommunications 
                  organization standard TR 45.6 Accounting Model for 
                  details."
         ::= { cCdmaSessionEntry 14 }     

cCdmaSessionRcvdOctets OBJECT-TYPE
         SYNTAX      ZeroBasedCounter32
         MAX-ACCESS  read-only
         STATUS      obsolete
         DESCRIPTION      
                 "The number of data octets received from the mobile 
                  user since session established."
         REFERENCE
                 "Refer to TIA/EIA international telecommunications 
                  organization standard TR 45.6 Accounting Model for
                  details."
         ::= { cCdmaSessionEntry 15 }     
         
cCdmaSessionSentPkts OBJECT-TYPE
         SYNTAX      ZeroBasedCounter32
         MAX-ACCESS  read-only
         STATUS      obsolete
         DESCRIPTION      
                 "The number of data packets sent to the mobile user
                  since session established."
         REFERENCE
                 "Refer to TIA/EIA international telecommunications 
                  organization standard TR 45.6 Accounting Model for
                  details."
         ::= { cCdmaSessionEntry 16 }

cCdmaSessionRcvdPkts OBJECT-TYPE
         SYNTAX      ZeroBasedCounter32
         MAX-ACCESS  read-only
         STATUS      obsolete
         DESCRIPTION      
                 "The number of data packets received from the mobile 
                  since session established."
         REFERENCE
                 "Refer to TIA/EIA international telecommunications 
                  organization standard TR 45.6 Accounting Model for
                  details."
         ::= { cCdmaSessionEntry 17 }

cCdmaSessionDiscardedOutPkts OBJECT-TYPE
         SYNTAX      ZeroBasedCounter32
         MAX-ACCESS  read-only
         STATUS      obsolete
         DESCRIPTION      
                 "The number of outgoing data packets dropped by PDSN
                  since system was last restarted."
         REFERENCE
                 "Refer to TIA/EIA international telecommunications 
                  organization standard TR 45.6 Accounting Model for
                  details."
         ::= { cCdmaSessionEntry 18 }     

cCdmaSessionDiscardedInPkts OBJECT-TYPE
         SYNTAX      ZeroBasedCounter32
         MAX-ACCESS  read-only
         STATUS      obsolete
         DESCRIPTION      
                 "The number of incoming data packets dropped by PDSN
                  since system was last restarted."
         REFERENCE
                 "Refer to TIA/EIA international telecommunications 
                  organization standard TR 45.6 0Accounting Model for 
                  details."
         ::= { cCdmaSessionEntry 19 }     
           
cCdmaSessionConnStartTime OBJECT-TYPE
         SYNTAX      DateAndTime
         MAX-ACCESS  read-only
         STATUS      obsolete
         DESCRIPTION 
                 "Indicates starting date and time of a session.  This 
                  value is provided by the RAN.  The agent is only 
                  propagating this information."
         ::= { cCdmaSessionEntry 20 }    

cCdmaActiveConnTime OBJECT-TYPE
         SYNTAX      Unsigned32
         UNITS       "seconds"
         MAX-ACCESS  read-only
         STATUS      obsolete
         DESCRIPTION 
                 "Amount of time while a session was established minus 
                  amount of time while the session was inactive on the 
                  RAN (no data channel assigned on the RAN)."
         ::= { cCdmaSessionEntry 21 }    

cCdmaSessionFlowCount OBJECT-TYPE
         SYNTAX      Gauge32
         MAX-ACCESS  read-only
         STATUS      obsolete
         DESCRIPTION                
                 "Number of existing IP flows for an established session."
         ::= { cCdmaSessionEntry 22 }

cCdmaSessionStatus     OBJECT-TYPE
         SYNTAX      INTEGER {
                      unknown(1),
                      airlinksetup(2),
                      airlinkstart(3),
                      airlinkstop(4)
         }
         MAX-ACCESS  read-only
         STATUS      obsolete
         DESCRIPTION   
                 "Session Status, airlinksetup(2), airlinkstart(3), 
                  airlinkstop(4)."
         REFERENCE
                 "Refer to TIA/EIA international telecommunications 
                  organization standard TR 45.6 Accounting Model for 
                  details."
         ::= { cCdmaSessionEntry 23 }

cCdmaSessionRegLifeTime  OBJECT-TYPE
         SYNTAX      TimeTicks
         MAX-ACCESS  read-only
         STATUS      obsolete
         DESCRIPTION   
                 "The amount of time, measured in hundredths of a 
                  second, granted before registration is considered 
                  expired."
         ::= { cCdmaSessionEntry 24 }

cCdmaSessionRegTimeToExpire OBJECT-TYPE
         SYNTAX      TimeTicks
         MAX-ACCESS  read-only
         STATUS      obsolete
         DESCRIPTION   
                 "The amount of time, measured in hundredths of a 
                  second, remaining before registration is considered 
                  expired."
         ::= { cCdmaSessionEntry 25 }

cCdmaSessionGREFromIPPkts OBJECT-TYPE
         SYNTAX      ZeroBasedCounter32
         MAX-ACCESS  read-only
         STATUS      obsolete
         DESCRIPTION   
                 "Number of GRE encapsulated packets received from IP
                  since system was last restarted."
        REFERENCE
                 "Refer to TIA/EIA international telecommunications 
                  organization standard TR 45.6 Accounting Model for 
                  details."
         ::= { cCdmaSessionEntry 26 }

cCdmaSessionGREToIPPkts OBJECT-TYPE
         SYNTAX      ZeroBasedCounter32
         MAX-ACCESS  read-only
         STATUS      obsolete
         DESCRIPTION   
                 "Number of GRE encapsulated packets delivered 
                  to IP for transmission since system was last 
                  restarted."
        REFERENCE
                 "Refer to TIA/EIA international telecommunications 
                  organization standard TR 45.6 Accounting Model for 
                  details."
         ::= { cCdmaSessionEntry 27 }

-- ******************************************************************
-- * CDMA PDSN IP flows table
-- ******************************************************************
  
cCdmaSessionFlowTable OBJECT-TYPE
         SYNTAX      SEQUENCE OF CCdmaSessionFlowEntry
         MAX-ACCESS  not-accessible
         STATUS      obsolete
         DESCRIPTION
                 "PDSN IP flows table.  Each entry is created when a new
                  conversation is initiated  between a MS and a HA.  A 
                  flow is linked to a PDSN session.  An IP flow is 
                  deleted when the conversation or the PDSN session is 
                  dismantled."
         ::= { cCdmaSessionInfo 2 }

cCdmaSessionFlowEntry OBJECT-TYPE
         SYNTAX      CCdmaSessionFlowEntry
         MAX-ACCESS  not-accessible
         STATUS      obsolete
         DESCRIPTION
                 "A conceptual row in the PDSN IP flow table."
         INDEX { cCdmaSessionMsid, cCdmaSessionUserFlowIpAddress}
         ::= { cCdmaSessionFlowTable 1 }
  
CCdmaSessionFlowEntry ::=
         SEQUENCE {
             cCdmaSessionUserFlowIpAddress       IpAddress,
             cCdmaSessionNai                     SnmpAdminString,
             cCdmaSessionAddressingScheme        INTEGER,
             cCdmaSessionFlowTechnology          INTEGER,
             cCdmaSessionHaIpAddress             IpAddress,
             cCdmaSessionTunnelProt              INTEGER
         }


cCdmaSessionUserFlowIpAddress OBJECT-TYPE
         SYNTAX      IpAddress
         MAX-ACCESS  not-accessible
         STATUS      obsolete
         DESCRIPTION   
                 "User flow Ip address."
         ::= { cCdmaSessionFlowEntry 1 }      

cCdmaSessionNai     OBJECT-TYPE
         SYNTAX      SnmpAdminString
         MAX-ACCESS  read-only
         STATUS      obsolete
         DESCRIPTION   
                 "Network Access Identifier of the user.  User@domain 
                  construct which identifies the home network of the 
                  mobile user."
         REFERENCE
                 "Refer to IETF RFC 2486 for more details."
         ::= { cCdmaSessionFlowEntry 2 } 

cCdmaSessionAddressingScheme OBJECT-TYPE
         SYNTAX      INTEGER {
                     other(1),
                     static(2),
                     dynamic(3)
                     }
         MAX-ACCESS  read-only
         STATUS      obsolete
         DESCRIPTION 
                 "Indicates MS IP address type:

                    - 'static' MS has a static IP address configured

                    - 'dynamic' MS is dynamically assigned an IP address

                    - 'other' in other cases"
         ::= { cCdmaSessionFlowEntry 3 } 

cCdmaSessionFlowTechnology OBJECT-TYPE
         SYNTAX      INTEGER {
                     other(1),
                     simpleIp(2),
                     mobileIp(3),
                     proxyMobileIp(4)
                     }
         MAX-ACCESS  read-only
         STATUS      obsolete
         DESCRIPTION
                 "Routing technology used by a flow:

                    - 'simpleIp' indicates IP routing

                    - 'mobileIp' indicates MoIP routing

                    - 'proxyMobileIp' indicates MoIP routing with PDSN acting
                      as a proxy MC.

                    - 'other' in other cases"
         ::= { cCdmaSessionFlowEntry 4 }         
  
cCdmaSessionHaIpAddress OBJECT-TYPE
         SYNTAX      IpAddress
         MAX-ACCESS  read-only
         STATUS      obsolete
         DESCRIPTION   
                 "MoIP home agent address.  Relevant only if MoIP or proxy
                  MoIP are used.
                 "
         ::= { cCdmaSessionFlowEntry 5 } 

cCdmaSessionTunnelProt OBJECT-TYPE
         SYNTAX      INTEGER {
                     other(1),
                     notunnel(2),
                     l2tp(3),
                     l2f(4),
                     gre(5),
                     ipinip(6)
                     }
         MAX-ACCESS  read-only
         STATUS      obsolete
         DESCRIPTION 
                 "Tunneling protocol used between MS and PDSN:

                    - 'notunnel' indicates no tunnel encapsulation

                    - 'l2tp' indicates tunnel encapsulation using l2tp protocol

                    - 'l2f' indicates tunnel encapsulation using l2f protocol

                    - 'gre' indicates tunnel encapsulation using
                      GRE protocol for mobileip

                    - 'ip-in-ip' indicates tunnel encapsulation using
                       IP-in-IP protocol for mobile

                    - 'other' in other cases"
         ::= { cCdmaSessionFlowEntry 6 }


-- ******************************************************************
-- * CDMA mobile user failures information
-- ******************************************************************
  
cCdmaFailHistInfoTable OBJECT-TYPE
         SYNTAX      SEQUENCE OF CCdmaFailHistInfoEntry
         MAX-ACCESS  not-accessible
         STATUS      current
         DESCRIPTION
                 "Session failures table.  An entry is created for 
                  every failed session.  cCdmaSessionPdsnMaxFailHistory
                  determines the maximum number of entries kept in this
                  table.  Once the table reaches the limit set, the 
                  oldest entries will be discarded to allow new entries
                  to be recorded."
         ::= { cCdmaFailHistInfo 1 }
  
cCdmaFailHistInfoEntry OBJECT-TYPE
         SYNTAX      CCdmaFailHistInfoEntry
         MAX-ACCESS  not-accessible
         STATUS      current
         DESCRIPTION
                 "A conceptual row in the PDSN Failure table."
         INDEX { cCdmaFailSessionIndex }
         ::= { cCdmaFailHistInfoTable 1 }
  
CCdmaFailHistInfoEntry ::=
         SEQUENCE {
             cCdmaFailSessionIndex       Unsigned32,
             cCdmaFailSessionMsid        OCTET STRING,
             cCdmaFailSessionMsidType    CCdmaMsidType,
             cCdmaFailSessionEsn         OCTET STRING,
             cCdmaFailSessionA11HaIp     IpAddress,
             cCdmaFailSessionA11FaIp     IpAddress,
             cCdmaFailSessionConnId      OCTET STRING,
             cCdmaFailSessionKey         OCTET STRING,
             cCdmaFailHistFailTime       DateAndTime,
             cCdmaFailHistFailType       INTEGER,
             cCdmaFailHistServiceOption  Unsigned32,
             cCdmaFailHistPanId          SnmpAdminString,
             cCdmaFailHistCanId          SnmpAdminString,
             cCdmaFailHistBsid           SnmpAdminString,
             cCdmaFailSessionEsn2        OCTET STRING             
         }
  
cCdmaFailSessionIndex OBJECT-TYPE
         SYNTAX      Unsigned32
         MAX-ACCESS  not-accessible
         STATUS      current
         DESCRIPTION
                 "An arbitrary integer to uniquely identify this entry.
                  Increases monotonically then wrap to zero."
         ::= { cCdmaFailHistInfoEntry 1 }

cCdmaFailSessionMsid OBJECT-TYPE
         SYNTAX      OCTET STRING (SIZE(5..15))
         MAX-ACCESS  read-only
         STATUS      current
         DESCRIPTION
                 "MSID of the mobile station for the failed session."
         ::= { cCdmaFailHistInfoEntry 2 }

cCdmaFailSessionMsidType OBJECT-TYPE
         SYNTAX      CCdmaMsidType
         MAX-ACCESS  read-only 
         STATUS      current
         DESCRIPTION   
                 "MSID format type of a mobile station for the failed 
                  session."
         ::= { cCdmaFailHistInfoEntry 3 }

cCdmaFailSessionEsn OBJECT-TYPE
         SYNTAX      OCTET STRING (SIZE(4))
         MAX-ACCESS  read-only
         STATUS      deprecated
         DESCRIPTION
                 "Electronic serial number of the mobile user for the 
                  failed session."
         ::= { cCdmaFailHistInfoEntry 4 }

cCdmaFailSessionA11HaIp OBJECT-TYPE
         SYNTAX      IpAddress
         MAX-ACCESS  read-only
         STATUS      current
         DESCRIPTION   
                 "MoIP Home Agent address on the A11 interface for the 
                  failed session."
         ::= { cCdmaFailHistInfoEntry 5  }          

cCdmaFailSessionA11FaIp OBJECT-TYPE
         SYNTAX      IpAddress
         MAX-ACCESS  read-only
         STATUS      current
         DESCRIPTION   
                 "MoIP Foreign Agent address on the A11 interface for the
                  failed session."
         ::= { cCdmaFailHistInfoEntry 6  }               
  
cCdmaFailSessionConnId  OBJECT-TYPE
         SYNTAX      OCTET STRING (SIZE(4))
         MAX-ACCESS  read-only 
         STATUS      current
         DESCRIPTION   
                 "Connection ID of the failed session."
         ::= { cCdmaFailHistInfoEntry 7 }

cCdmaFailSessionKey  OBJECT-TYPE
         SYNTAX      OCTET STRING (SIZE(4))
         MAX-ACCESS  read-only 
         STATUS      current
         DESCRIPTION   
                 "GRE session identification key of the failed session."
         ::= { cCdmaFailHistInfoEntry 8 }

cCdmaFailHistFailTime OBJECT-TYPE
        SYNTAX     DateAndTime
        MAX-ACCESS read-only
        STATUS     current
        DESCRIPTION
                "Date and time of the failure occurrence."
        ::= { cCdmaFailHistInfoEntry 9 }

cCdmaFailHistFailType OBJECT-TYPE
         SYNTAX      INTEGER {
                     other(1),
                     pppAuthenticationFailure(2),
                     mobileIpAuthenticationFailure(3),
                     mobileIpRegistrationTimeout(4),
                     a10a11SessionTimeout(5),
                     maxAllowedSessionReached(6),
                     maxAllowedPcfReached(7),
                     sessionFormatError(8),
                     adminProhibited(9),
                     insufficientResource(10),
                     mnAuthenticationFailed(11),
                     registrationIdentMismatched(12),
                     poorlyFormedRequest(13),
                     unknownHAAddress(14),
                     reverseTunnelUnavail(15),
                     tbitNotSet(16),
                     unsupportedVIDorBadCVSE(17),
                     pppLcpTimeout(18),
                     pppLcpNegotiationFailed(19),
                     pppIpcpTimeout(20),
                     pppIpcpNegotiationFailed(21)
                     }
         MAX-ACCESS  read-only
         STATUS      current
         DESCRIPTION
                 "Type of failure for the current record."
         ::= { cCdmaFailHistInfoEntry 10 }
         
cCdmaFailHistServiceOption OBJECT-TYPE
        SYNTAX     Unsigned32 (1..4294967295)
        MAX-ACCESS read-only
        STATUS     current
        DESCRIPTION
                "A Packet Data Service Option, which provides a means
                between MS and RN to establish and maintain cdma2000
                traffic channels for packet data service."
        ::= { cCdmaFailHistInfoEntry 11 }
        
cCdmaFailHistPanId OBJECT-TYPE
        SYNTAX     SnmpAdminString (SIZE(10))
        MAX-ACCESS read-only
        STATUS     current
        DESCRIPTION
                "The identifier of the previous network equipment
                that provided data connectivity between PDSN and
                the MS."
        ::= { cCdmaFailHistInfoEntry 12 }

cCdmaFailHistCanId OBJECT-TYPE       
        SYNTAX     SnmpAdminString (SIZE(10))
        MAX-ACCESS read-only
        STATUS     current
        DESCRIPTION
                "The identifier of the current network equipment
                that provides data connectivity between PDSN and
                the MS."
        ::= { cCdmaFailHistInfoEntry 13 }
        
cCdmaFailHistBsid OBJECT-TYPE
        SYNTAX     SnmpAdminString (SIZE(12))
        MAX-ACCESS read-only
        STATUS     current
        DESCRIPTION
                "The identifier of Base Station that enables radio
                communication with the MS."
        ::= { cCdmaFailHistInfoEntry 14 }

cCdmaFailSessionEsn2 OBJECT-TYPE
         SYNTAX      OCTET STRING (SIZE(16))
         MAX-ACCESS  read-only
         STATUS      current
         DESCRIPTION
                 "Electronic serial number of the mobile user for the 
                  failed session."
         ::= { cCdmaFailHistInfoEntry 15 }

-- ******************************************************************
-- * CDMA PDSN Registration Statistics
-- ******************************************************************

cCdmaRPRegValidRequests OBJECT-TYPE
        SYNTAX      ZeroBasedCounter32
        MAX-ACCESS  read-only
        STATUS      obsolete
        DESCRIPTION
                "The number of valid Registration Requests Received
                 since system was last restarted."
        REFERENCE
                 "Refer to TIA/EIA international telecommunications 
                  organization standard TR 45.4 for details about 
                  A10/A11(R-P) interface."
        ::= { cCdmaRPRegistrationStats 1 }

cCdmaRPRegAcceptedReplies OBJECT-TYPE
        SYNTAX      ZeroBasedCounter32
        MAX-ACCESS  read-only
        STATUS      obsolete
        DESCRIPTION
                "The number of registration replies accepted
                 since system was last restarted."
        REFERENCE
                 "Refer to TIA/EIA international telecommunications 
                  organization standard TR 45.4 for details about 
                  A10/A11(R-P) interface."
        ::= { cCdmaRPRegistrationStats 2 }

cCdmaRPRegLifeTimeZeroRequests OBJECT-TYPE
        SYNTAX      ZeroBasedCounter32
        MAX-ACCESS  read-only
        STATUS      obsolete
        DESCRIPTION
                "The number of valid registration requests received with
                 life time zero since system was last restarted."
        REFERENCE
                 "Refer to TIA/EIA international telecommunications 
                  organization standard TR 45.4 for details about 
                  A10/A11(R-P) interface."
        ::= { cCdmaRPRegistrationStats 3 }

cCdmaRPDeRegAcceptedReplies OBJECT-TYPE
        SYNTAX      ZeroBasedCounter32
        MAX-ACCESS  read-only
        STATUS      obsolete
        DESCRIPTION
                "The number of valid registration requests with life
                 time zero accepted since system was last restarted."
        REFERENCE
                 "Refer to TIA/EIA international telecommunications 
                  organization standard TR 45.4 for details about 
                  A10/A11(R-P) interface."
        ::= { cCdmaRPRegistrationStats 4 }

cCdmaRPRegReasonUnSpecFailures OBJECT-TYPE
        SYNTAX      ZeroBasedCounter32
        MAX-ACCESS  read-only
        STATUS      obsolete
        DESCRIPTION
                "The number of registration requests failed because PCF
                 address not in PDSN's list of configured PCFs for 
                 unspecified reason since system was last restarted."
        REFERENCE
                 "Refer to TIA/EIA international telecommunications 
                  organization standard TR 45.4 for details about A10 
                  session setup errors."
        ::= { cCdmaRPRegistrationStats 5 }

cCdmaRPRegAdminProhibFailures OBJECT-TYPE
        SYNTAX      ZeroBasedCounter32
        MAX-ACCESS  read-only
        STATUS      obsolete
        DESCRIPTION
                "The number of registration requests failed because PCF
                 address is not in PDSN's list of configured PCFs since
                 system was last restarted."
        REFERENCE
                 "Refer to TIA/EIA international telecommunications 
                  organization standard TR 45.4 for details about A10 
                  session setup errors."
        ::= { cCdmaRPRegistrationStats 6 }

cCdmaRPRegInsuffResFailures OBJECT-TYPE
        SYNTAX      ZeroBasedCounter32
        MAX-ACCESS  read-only
        STATUS      obsolete
        DESCRIPTION
                "The number of registration requests failed because
                 of insufficient resources since the system was last
                 restarted.  Factors causing insufficient resources may
                 be due to the max number of PCFs, the max number of 
                 sessions reached, or exhaustion of other system 
                 resources."
        REFERENCE
                 "Refer to TIA/EIA international telecommunications 
                  organization standard TR 45.4 for details about A10 
                  session setup errors."
        ::= { cCdmaRPRegistrationStats 7 }

cCdmaRPRegMNAuthenFailures OBJECT-TYPE
        SYNTAX      ZeroBasedCounter32
        MAX-ACCESS  read-only
        STATUS      obsolete
        DESCRIPTION
                "The number of registration requests failed due to 
                 MN authentication failure since system was last 
                 restarted."
        REFERENCE
                 "Refer to TIA/EIA international telecommunications 
                  organization standard TR 45.4 for details about A10 
                  session setup errors."
        ::= { cCdmaRPRegistrationStats 8 }

cCdmaRPRegIdentMismatchFailures OBJECT-TYPE
        SYNTAX      ZeroBasedCounter32
        MAX-ACCESS  read-only
        STATUS      obsolete
        DESCRIPTION
                "The number of registration requests failed because 
                 of identification mismatch since system was last 
                 restarted."
        REFERENCE
                 "Refer to TIA/EIA international telecommunications 
                  organization standard TR 45.4 for details about A10 
                  session setup errors."
        ::= { cCdmaRPRegistrationStats 9 }

cCdmaRPRegBadRequestFailures OBJECT-TYPE
        SYNTAX      ZeroBasedCounter32
        MAX-ACCESS  read-only
        STATUS      obsolete
        DESCRIPTION
                "The number of registration requests failed 
                 because of badly formed request since system was last
                 restarted."
        REFERENCE
                 "Refer to TIA/EIA international telecommunications 
                  organization standard TR 45.4 for details about A10 
                  session setup errors."
        ::= { cCdmaRPRegistrationStats 10 }

cCdmaRPRegUnknownHAAddrFailures OBJECT-TYPE
        SYNTAX      ZeroBasedCounter32
        MAX-ACCESS  read-only
        STATUS      obsolete
        DESCRIPTION
                "The number of registration requests failed 
                 because of unknown Home Agent Address since system was
                 last restarted."
        REFERENCE
                 "Refer to TIA/EIA international telecommunications 
                  organization standard TR 45.4 for details about A10 
                  session setup errors."
        ::= { cCdmaRPRegistrationStats 11 }

cCdmaRPRegNoRevTunnelFailures OBJECT-TYPE
        SYNTAX      ZeroBasedCounter32
        MAX-ACCESS  read-only
        STATUS      obsolete
        DESCRIPTION
                "The number of registration requests  failed because 
                 FA to HA tunnel setup failed since system was last
                 restarted."
        REFERENCE
                 "RFC-2344."
        ::= { cCdmaRPRegistrationStats 12 }

cCdmaRPRegTBitNotSetFailures OBJECT-TYPE
        SYNTAX      ZeroBasedCounter32
        MAX-ACCESS  read-only
        STATUS      obsolete
        DESCRIPTION
                "The number of registration requests failed because 
                 Reverse Tunnel bit Not set since system was last 
                 restarted."
        REFERENCE
                 "Refer to TIA/EIA international telecommunications 
                  organization standard TR 45.4 for details about A10 
                  session setup errors."
        ::= { cCdmaRPRegistrationStats 13 }

cCdmaRPRegBadCVSEFailures OBJECT-TYPE
        SYNTAX      ZeroBasedCounter32
        MAX-ACCESS  read-only
        STATUS      obsolete
        DESCRIPTION
                "The number of registration requests failed because of 
                 unsupported vendor codes in CVSE since system was last
                 restarted."
        REFERENCE
                 "Refer to TIA/EIA international telecommunications 
                  organization standard TR 45.4 for details about A10 
                  session setup errors."
        ::= { cCdmaRPRegistrationStats 14 }

-- ******************************************************************
-- * CDMA PDSN Update Registration Statistics
-- ******************************************************************

cCdmaRPUpdValidRequests OBJECT-TYPE
        SYNTAX      ZeroBasedCounter32
        MAX-ACCESS  read-only
        STATUS      obsolete
        DESCRIPTION
                "The number of valid update registration requests 
                 received since system was last restarted."
        REFERENCE
                 "Refer to TIA/EIA international telecommunications 
                  organization standard TR 45.4 for A10 session update 
                  message and TR 45.6 for Accounting Model."
        ::= { cCdmaRPUpdateStats 1 }


cCdmaRPUpdAcceptedReplies OBJECT-TYPE
        SYNTAX      ZeroBasedCounter32
        MAX-ACCESS  read-only
        STATUS      obsolete
        DESCRIPTION
                "The number of valid update registration replies 
                 accepted since system was last restarted."
        REFERENCE
                 "Refer to TIA/EIA international telecommunications 
                  organization standard TR 45.4 for A10 session update 
                  message and TR 45.6 for Accounting Model."
        ::= { cCdmaRPUpdateStats 2 }

cCdmaRPUpdReasonUnSpecFailures OBJECT-TYPE
        SYNTAX      ZeroBasedCounter32
        MAX-ACCESS  read-only
        STATUS      obsolete
        DESCRIPTION
                "The number of update registrations failed for 
                 unspecified reason since system was last restarted."
        REFERENCE
                 "Refer to TIA/EIA international telecommunications 
                  organization standard TR 45.4 for details about A10 
                  session setup errors."
        ::= { cCdmaRPUpdateStats 3 }

cCdmaRPUpdAdminProhibFailures OBJECT-TYPE
        SYNTAX      ZeroBasedCounter32
        MAX-ACCESS  read-only
        STATUS      obsolete
        DESCRIPTION
                "The number of update registrations failed due to 
                 administrative prohibition since system was last 
                 restarted."
        REFERENCE
                 "Refer to TIA/EIA international telecommunications 
                  organization standard TR 45.4 for details about A10 
                  session setup errors."
        ::= { cCdmaRPUpdateStats 4 }

cCdmaRPUpdMNAuthenFailures OBJECT-TYPE
        SYNTAX      ZeroBasedCounter32
        MAX-ACCESS  read-only
        STATUS      obsolete
        DESCRIPTION
                "The number of update registrations failed due to MN 
                 authentication failure since system was last 
                 restarted."
        REFERENCE
                 "Refer to TIA/EIA international telecommunications 
                  organization standard TR 45.4 for details about A10 
                  session setup errors."
        ::= { cCdmaRPUpdateStats 5 }

cCdmaRPUpdIdentMismatchFailures OBJECT-TYPE
        SYNTAX      ZeroBasedCounter32
        MAX-ACCESS  read-only
        STATUS      obsolete
        DESCRIPTION
                "The number of registrations failed due to registration
                 identity mismatch since system was last restarted."
        REFERENCE
                 "Refer to TIA/EIA international telecommunications 
                  organization standard TR 45.4 for details about A10 
                  session setup errors."
        ::= { cCdmaRPUpdateStats 6 }

cCdmaRPUpdBadRequestFailures OBJECT-TYPE
        SYNTAX      ZeroBasedCounter32
        MAX-ACCESS  read-only
        STATUS      obsolete
        DESCRIPTION
                "The number of update registrations failed due to 
                 poorly formed request since system was last restarted."
        REFERENCE
                 "Refer to TIA/EIA international telecommunications 
                  organization standard TR 45.4 for details about A10 
                  session setup errors."
        ::= { cCdmaRPUpdateStats 7 }


-- ******************************************************************
-- * CDMA PDSN Registration Statistics for PDSN Release 1.1 and newer
-- ******************************************************************

cCdmaRpRegReceivedReqs OBJECT-TYPE
        SYNTAX      Counter32
        MAX-ACCESS  read-only
        STATUS      current
        DESCRIPTION
                "Total number of A11 Registration Requests received
                 since the system was last restarted. "
        REFERENCE
                 "Refer to TIA/EIA international telecommunications
                  organization standard TR 45.4 for details about
                  A10/A11(R-P) interface."
        ::= { cCdmaRpRegStats 1 }

cCdmaRpRegAcceptedReqs OBJECT-TYPE
        SYNTAX      Counter32
        MAX-ACCESS  read-only
        STATUS      current
        DESCRIPTION
                "Total number of A11 Registration Requests accepted
                 since the system was last restarted. The Code field
                 in the corresponding Registration Reply message, is
                 set to zero. "
        REFERENCE
                 "Refer to TIA/EIA international telecommunications
                  organization standard TR 45.4 for details about
                  A10/A11(R-P) interface."
        ::= { cCdmaRpRegStats 2 }

cCdmaRpRegDeniedReqs OBJECT-TYPE
        SYNTAX      Counter32
        MAX-ACCESS  read-only
        STATUS      current
        DESCRIPTION
                "Total number of A11 Registration Requests denied
                 since the system was last restarted. The Code field
                 in the corresponding Registration Reply message is
                 set to non-zero. "
        REFERENCE
                 "Refer to TIA/EIA international telecommunications

                  organization standard TR 45.4 for details about
                  A10/A11(R-P) interface."
        ::= { cCdmaRpRegStats 3 }

cCdmaRpRegDiscardedReqs OBJECT-TYPE
        SYNTAX      Counter32
        MAX-ACCESS  read-only
        STATUS      current
        DESCRIPTION
                "Total number of A11 Registration Requests silently
                 discarded  since the system was last restarted. A
                 corresponding Registration Reply message is not
                 returned for these A11 Registration Requests."
        REFERENCE
                 "Refer to TIA/EIA international telecommunications
                  organization standard TR 45.4 for details about
                  A10/A11(R-P) interface."
        ::= { cCdmaRpRegStats 4 }

cCdmaRpInitRegAcceptedReqs OBJECT-TYPE
        SYNTAX      Counter32
        MAX-ACCESS  read-only
        STATUS      current
        DESCRIPTION
                "Total number of accepted A11 Registration Requests
                 meant for establishing new R-P connections or 
                 Registration Requests with GRE key different from 
                 that of already existing session, since the system 
                 was last restarted. These A11 Registration Requests 
                 contain the Connection Setup Airlink Record. The 
                 Code field in the corresponding Registration 
                 Reply message is set to zero."
        REFERENCE
                 "Refer to TIA/EIA international telecommunications
                  organization standard TR 45.4 for details about
                  A10/A11(R-P) interface."
        ::= { cCdmaRpRegStats 5 }

cCdmaRpInitRegDeniedReqs OBJECT-TYPE
        SYNTAX      Counter32
        MAX-ACCESS  read-only
        STATUS      current
        DESCRIPTION
                "Total number of denied A11 Registration Requests
                 meant for establishing new R-P connections or 
                 Registration Requests with GRE key different from 
                 that of already existing session, since the system 
                 was last restarted. These A11 Registration Requests 
                 contain the Connection Setup Airlink Record. The 
                 Code field in the corresponding Registration 
                 Reply message is set to zero."

        REFERENCE
                 "Refer to TIA/EIA international telecommunications
                  organization standard TR 45.4 for details about
                  A10/A11(R-P) interface."
        ::= { cCdmaRpRegStats 6 }

cCdmaRpReRegAcceptedReqs OBJECT-TYPE
        SYNTAX      Counter32
        MAX-ACCESS  read-only
        STATUS      current
        DESCRIPTION
                "Total number of accepted A11 Registration Requests
                 meant for refreshing the already established R-P
                 connections, since the system was last restarted. The
                 Code field in the corresponding Registration Reply
                 message is set to zero."
        REFERENCE
                 "Refer to TIA/EIA international telecommunications
                  organization standard TR 45.4 for details about
                  A10/A11(R-P) interface."
        ::= { cCdmaRpRegStats 7 }

cCdmaRpReRegDeniedReqs OBJECT-TYPE
        SYNTAX      Counter32
        MAX-ACCESS  read-only
        STATUS      current
        DESCRIPTION
                "Total number of denied A11 Registration Requests
                 meant for refreshing the already established R-P
                 connections, since the system was last restarted. The
                 Code field in the corresponding Registration Reply
                 message is set to non-zero."
        REFERENCE
                 "Refer to TIA/EIA international telecommunications
                  organization standard TR 45.4 for details about
                  A10/A11(R-P) interface."
        ::= { cCdmaRpRegStats 8 }

cCdmaRpDeRegAcceptedReqs OBJECT-TYPE
        SYNTAX      Counter32
        MAX-ACCESS  read-only
        STATUS      current
        DESCRIPTION
                "Total number of accepted A11 Registration Requests
                 meant for de-establishing the already established R-P
                 connections, since the system was last restarted. The
                 Code field in the corresponding Registration Reply
                 message is set to zero."
        REFERENCE
                 "Refer to TIA/EIA international telecommunications
                  organization standard TR 45.4 for details about
                  A10/A11(R-P) interface."
        ::= { cCdmaRpRegStats 9 }

cCdmaRpDeRegDeniedReqs OBJECT-TYPE
        SYNTAX      Counter32
        MAX-ACCESS  read-only
        STATUS      current
        DESCRIPTION
                "Total number of denied A11 Registration Requests
                 meant for de-establishing the already established R-P
                 connections, since the system was last restarted. The
                 Code field in the corresponding Registration Reply
                 message is set to non-zero."
        REFERENCE
                 "Refer to TIA/EIA international telecommunications
                  organization standard TR 45.4 for details about
                  A10/A11(R-P) interface."
        ::= { cCdmaRpRegStats 10 }

cCdmaRpRegReasonlUnSpecFailures OBJECT-TYPE
        SYNTAX      Counter32
        MAX-ACCESS  read-only
        STATUS      deprecated
        DESCRIPTION
                "The number of registration requests failed because PCF
                 address not in PDSN's list of configured PCFs for
                 unspecified reason since system was last restarted."
        REFERENCE
                 "Refer to TIA/EIA international telecommunications
                  organization standard TR 45.4 for details about A10
                  session setup errors."
        ::= { cCdmaRpRegStats 11 }

cCdmaRpRegAdminProhibFailures OBJECT-TYPE
        SYNTAX      Counter32
        MAX-ACCESS  read-only
        STATUS      current
        DESCRIPTION
                "The number of registration requests failed because PCF
                 address is not in PDSN's list of configured PCFs since
                 system was last restarted."
        REFERENCE
                 "Refer to TIA/EIA international telecommunications

                  organization standard TR 45.4 for details about A10
                  session setup errors."
        ::= { cCdmaRpRegStats 12 }

cCdmaRpRegInsuffResFailures OBJECT-TYPE
        SYNTAX      Counter32
        MAX-ACCESS  read-only
        STATUS      current
        DESCRIPTION
                "The number of registration requests failed because
                 max number of PCFs or max number of sessions reached
                 or out of system resources since system was last
                 restarted."
        REFERENCE
                 "Refer to TIA/EIA international telecommunications
                  organization standard TR 45.4 for details about A10
                  session setup errors."
        ::= { cCdmaRpRegStats 13 }

cCdmaRpRegMNAuthFailures OBJECT-TYPE
        SYNTAX      Counter32
        MAX-ACCESS  read-only
        STATUS      current
        DESCRIPTION
                "The number of registration requests failed due to
                 MN authentication failure since system was last
                 restarted."
        REFERENCE
                 "Refer to TIA/EIA international telecommunications
                  organization standard TR 45.4 for details about A10
                  session setup errors."
        ::= { cCdmaRpRegStats 14 }

cCdmaRpRegIdMismatchFailures OBJECT-TYPE
        SYNTAX      Counter32
        MAX-ACCESS  read-only
        STATUS      current
        DESCRIPTION
                "The number of registration requests failed because
                 of identification mismatch since system was last
                 restarted."
        REFERENCE
                 "Refer to TIA/EIA international telecommunications
                  organization standard TR 45.4 for details about A10
                  session setup errors."
        ::= { cCdmaRpRegStats 15 }

cCdmaRpRegBadReqFailures OBJECT-TYPE

        SYNTAX      Counter32
        MAX-ACCESS  read-only
        STATUS      current
        DESCRIPTION
                "The number of registration requests failed
                 because of badly formed request since system was last
                 restarted."
        REFERENCE
                 "Refer to TIA/EIA international telecommunications
                  organization standard TR 45.4 for details about A10
                  session setup errors."
        ::= { cCdmaRpRegStats 16 }

cCdmaRpRegUnknownPdsnFailures OBJECT-TYPE
        SYNTAX      Counter32
        MAX-ACCESS  read-only
        STATUS      current
        DESCRIPTION
                "The number of registration requests failed
                 because of unknown PDSN/HA Address since system was
                 last restarted."
        REFERENCE
                 "Refer to TIA/EIA international telecommunications
                  organization standard TR 45.4 for details about A10
                  session setup errors."
        ::= { cCdmaRpRegStats 17 }

cCdmaRpRegNoRevTunnelFailures OBJECT-TYPE
        SYNTAX      Counter32
        MAX-ACCESS  read-only
        STATUS      current
        DESCRIPTION
                "The number of registration requests failed because
                 FA to HA reverse tunnel setup failed since system was
                 last restarted."
        REFERENCE
                 "RFC-2344."
        ::= { cCdmaRpRegStats 18 }

cCdmaRpRegTBitNotSetFailures OBJECT-TYPE
        SYNTAX      Counter32
        MAX-ACCESS  read-only
        STATUS      current
        DESCRIPTION
                "The number of registration requests failed because
                 reverse tunnel is required, but T bit is not set since
                 system was last restarted."
        REFERENCE
                 "Refer to TIA/EIA international telecommunications
                  organization standard TR 45.4 for details about A10
                  session setup errors."
        ::= { cCdmaRpRegStats 19 }

cCdmaRpRegBadCVSEFailures OBJECT-TYPE
        SYNTAX      Counter32
        MAX-ACCESS  read-only
        STATUS      current
        DESCRIPTION
                "The number of registration requests failed because of
                 unsupported vendor codes in CVSE since system was last
                 restarted."
        REFERENCE
                 "Refer to TIA/EIA international telecommunications
                  organization standard TR 45.4 for details about A10
                  session setup errors."
        ::= { cCdmaRpRegStats 20 }

cCdmaRpRegReasonUnSpecFailures OBJECT-TYPE
        SYNTAX      Counter32
        MAX-ACCESS  read-only
        STATUS      current
        DESCRIPTION
                "The number of registration requests failed because PCF
                 address not in PDSN's list of configured PCFs for
                 unspecified reason since system was last restarted."
        REFERENCE
                 "Refer to TIA/EIA international telecommunications
                  organization standard TR 45.4 for details about A10
                  session setup errors."
        ::= { cCdmaRpRegStats 21 }

cCdmaRpDeRegHandoffAcceptedReqs OBJECT-TYPE        
        SYNTAX      Counter32
        MAX-ACCESS  read-only
        STATUS      current
        DESCRIPTION
                "Total number of accepted A11 Registration Requests
                 meant for de-establishing the already established R-P
                 connections with the PCF from which the MN was handed
                 off, since the system was last restarted. The
                 Code field in the corresponding Registration Reply
                 message is set to zero."
        REFERENCE
                 "Refer to TIA/EIA international telecommunications
                  organization standard TR 45.4 for details about A10
                  session setup errors."
        ::= { cCdmaRpRegStats 22 }

cCdmaRpDeRegHandoffDeniedReqs OBJECT-TYPE        
        SYNTAX      Counter32
        MAX-ACCESS  read-only
        STATUS      current
        DESCRIPTION
                "Total number of denied A11 Registration Requests
                 meant for de-establishing the already established R-P
                 connections with the PCF from which the MN was handed
                 off, since the system was last restarted. The
                 Code field in the corresponding Registration Reply
                 message is set to non-zero."
        REFERENCE
                 "Refer to TIA/EIA international telecommunications
                  organization standard TR 45.4 for details about
                  A10/A11(R-P) interface."
        ::= { cCdmaRpRegStats 23 }

cCdmaRpInitRegReceivedReqs OBJECT-TYPE
        SYNTAX      ZeroBasedCounter32
        MAX-ACCESS  read-only
        STATUS      current
        DESCRIPTION
                "The number of Initial A11 Registration requests 
                 received since system was last restarted."
        REFERENCE
                 "Refer to TIA/EIA international telecommunications 
                  organization standard TR 45.4 for details about A10 
                  session setup errors."
        ::= { cCdmaRpRegStats 24 }

cCdmaRpInitRegDiscardedReqs OBJECT-TYPE
        SYNTAX      ZeroBasedCounter32
        MAX-ACCESS  read-only
        STATUS      current
        DESCRIPTION
                "The number of Initial A11 Registration requests 
                 silently discarded since system was last restarted."
        REFERENCE
                 "Refer to TIA/EIA international telecommunications 
                  organization standard TR 45.4 for details about A10 
                  session setup errors."
        ::= { cCdmaRpRegStats 25 }

cCdmaRpReRegReceivedReqs OBJECT-TYPE
        SYNTAX      ZeroBasedCounter32
        MAX-ACCESS  read-only
        STATUS      current
        DESCRIPTION
                "The number of A11 Re-Registration requests 
                 received since system was last restarted."
        REFERENCE
                 "Refer to TIA/EIA international telecommunications 
                  organization standard TR 45.4 for details about A10 
                  session setup errors."
        ::= { cCdmaRpRegStats 26 }

cCdmaRpReRegDiscardedReqs OBJECT-TYPE
        SYNTAX      ZeroBasedCounter32
        MAX-ACCESS  read-only
        STATUS      current
        DESCRIPTION
                "The number of A11 Re-Registration requests 
                 silently discarded since system was last restarted."
        REFERENCE
                 "Refer to TIA/EIA international telecommunications 
                  organization standard TR 45.4 for details about A10 
                  session setup errors."
        ::= { cCdmaRpRegStats 27 }

cCdmaRpDeRegReceivedReqs OBJECT-TYPE
        SYNTAX      ZeroBasedCounter32
        MAX-ACCESS  read-only
        STATUS      current
        DESCRIPTION
                "The number of A11 De-Registration requests 
                 received since system was last restarted."
        REFERENCE
                 "Refer to TIA/EIA international telecommunications 
                  organization standard TR 45.4 for details about A10 
                  session setup errors."
        ::= { cCdmaRpRegStats 28 }

cCdmaRpDeRegDiscardedReqs OBJECT-TYPE
        SYNTAX      ZeroBasedCounter32
        MAX-ACCESS  read-only
        STATUS      current
        DESCRIPTION
                "The number of A11 De-Registration requests 
                 silently discarded since system was last restarted."
        REFERENCE
                 "Refer to TIA/EIA international telecommunications 
                  organization standard TR 45.4 for details about A10 
                  session setup errors."
        ::= { cCdmaRpRegStats 29 }

cCdmaRpHandoffRegReceivedReqs OBJECT-TYPE
        SYNTAX      ZeroBasedCounter32
        MAX-ACCESS  read-only
        STATUS      current
        DESCRIPTION
                "The number of A11 Handoff Registration requests 
                 received since system was last restarted."
        REFERENCE
                 "Refer to TIA/EIA international telecommunications 
                  organization standard TR 45.4 for details about A10 
                  session setup errors."
        ::= { cCdmaRpRegStats 30 }

cCdmaRpHandoffRegAcceptedReqs OBJECT-TYPE
        SYNTAX      ZeroBasedCounter32
        MAX-ACCESS  read-only
        STATUS      current
        DESCRIPTION
                "Total number of accepted handoff A11 Registration 
                 Requests meant for already existing session, since 
                 the system was last restarted."
        REFERENCE
                 "Refer to TIA/EIA international telecommunications
                  organization standard TR 45.4 for details about
                  A10/A11(R-P) interface."
        ::= { cCdmaRpRegStats 31 }

cCdmaRpHandoffRegDeniedReqs OBJECT-TYPE
        SYNTAX      ZeroBasedCounter32
        MAX-ACCESS  read-only
        STATUS      current
        DESCRIPTION
                "Total number of denied handoff A11 Registration 
                 Requests meant for already existing session, 
                 since the system was last restarted."

        REFERENCE
                 "Refer to TIA/EIA international telecommunications
                  organization standard TR 45.4 for details about
                  A10/A11(R-P) interface."
        ::= { cCdmaRpRegStats 32 }

cCdmaRpHandoffRegDiscardedReqs OBJECT-TYPE
        SYNTAX      ZeroBasedCounter32
        MAX-ACCESS  read-only
        STATUS      current
        DESCRIPTION
                "The number of handoff A11 Registration requests 
                 silently discarded since system was last restarted."
        REFERENCE
                 "Refer to TIA/EIA international telecommunications 
                  organization standard TR 45.4 for details about A10 
                  session setup errors."
        ::= { cCdmaRpRegStats 33 }

cCdmaRpReRegAirlinkStarts OBJECT-TYPE
        SYNTAX      ZeroBasedCounter32
        MAX-ACCESS  read-only
        STATUS      current
        DESCRIPTION
                "The number of A11 Re-Registration requests 
                 containing Airlink Start since system was last restarted."
        REFERENCE
                 "Refer to TIA/EIA international telecommunications 
                  organization standard TR 45.4 for details about A10 
                  session setup errors."
        ::= { cCdmaRpRegStats 34 }

cCdmaRpReRegAirlinkStops OBJECT-TYPE
        SYNTAX      ZeroBasedCounter32
        MAX-ACCESS  read-only
        STATUS      current
        DESCRIPTION
                "The number of A11 Re-Registration requests 
                 containing Airlink Stop since system was last restarted."
        REFERENCE
                 "Refer to TIA/EIA international telecommunications 
                  organization standard TR 45.4 for details about A10 
                  session setup errors."
        ::= { cCdmaRpRegStats 35 }

cCdmaRpDeRegAirlinkStops OBJECT-TYPE
        SYNTAX      ZeroBasedCounter32
        MAX-ACCESS  read-only
        STATUS      current
        DESCRIPTION
                "The number of A11 De-Registration requests 
                 containing Airlink Stop since system was last restarted."
        REFERENCE
                 "Refer to TIA/EIA international telecommunications 
                  organization standard TR 45.4 for details about A10 
                  session setup errors."
        ::= { cCdmaRpRegStats 36 }

cCdmaRpInterPCFActiveHandoffs OBJECT-TYPE
        SYNTAX      ZeroBasedCounter32
        MAX-ACCESS  read-only
        STATUS      current
        DESCRIPTION
                "The number of Inter PCF active handoff  
                 since system was last restarted."
        REFERENCE
                 "Refer to TIA/EIA international telecommunications 
                  organization standard TR 45.4 for details about A10 
                  session setup errors."
        ::= { cCdmaRpRegStats 37 }

cCdmaRpInterPCFDormantHandoffs OBJECT-TYPE
        SYNTAX      ZeroBasedCounter32
        MAX-ACCESS  read-only
        STATUS      current
        DESCRIPTION
                "The number of Inter PCF dormant handoff  
                 since system was last restarted."
        REFERENCE
                 "Refer to TIA/EIA international telecommunications 
                  organization standard TR 45.4 for details about A10 
                  session setup errors."
        ::= { cCdmaRpRegStats 38 }


-- ******************************************************************
-- * CDMA PDSN Update Registration Statistics
-- ******************************************************************

cCdmaRpUpdTransmittedReqs OBJECT-TYPE
        SYNTAX      Counter32
        MAX-ACCESS  read-only
        STATUS      current
        DESCRIPTION
                "Total number of A11 Registration Updates transmitted
                 since system was last restarted."
        REFERENCE
                 "Refer to TIA/EIA international telecommunications
                  organization standard TR 45.4 for A10 session update
                  message and TR 45.6 for Accounting Model."
        ::= { cCdmaRpUpdStats 1 }

cCdmaRpUpdAcceptedReqs OBJECT-TYPE
        SYNTAX      Counter32
        MAX-ACCESS  read-only
        STATUS      current
        DESCRIPTION
                "Total number of A11 Registration Acknowledgements
                 received with the Status field set to zero (indicating
                 that the corresponding Registration Update was
                 accepted), since system was last restarted."
        REFERENCE
                 "Refer to TIA/EIA international telecommunications
                  organization standard TR 45.4 for A10 session update
                  message and TR 45.6 for Accounting Model."
        ::= { cCdmaRpUpdStats 2 }

cCdmaRpUpdDeniedReqs OBJECT-TYPE
        SYNTAX      Counter32
        MAX-ACCESS  read-only
        STATUS      current
        DESCRIPTION
                "Total number of A11 Registration Acknowledgements
                 received with the Status field set to non-zero
                 indicating that the corresponding Registration Update
                 was denied, since system was last restarted."
        REFERENCE
                 "Refer to TIA/EIA international telecommunications
                  organization standard TR 45.4 for A10 session update
                  message and TR 45.6 for Accounting Model."
        ::= { cCdmaRpUpdStats 3 }

cCdmaRpUpdNotAckedReqs OBJECT-TYPE
        SYNTAX      Counter32
        MAX-ACCESS  read-only
        STATUS      current
        DESCRIPTION
                "Total number of A11 Registration Updates sent,
                 for which no corresponding A11 Registration
                 Acknowledgements received, since system was last
                 restarted."
        REFERENCE
                 "Refer to TIA/EIA international telecommunications
                  organization standard TR 45.4 for A10 session update
                  message and TR 45.6 for Accounting Model."
        ::= { cCdmaRpUpdStats 4 }

cCdmaRpUpdInitTransmittedReqs OBJECT-TYPE
        SYNTAX      Counter32
        MAX-ACCESS  read-only
        STATUS      current
        DESCRIPTION
                "Total number of initial A11 Registration Updates
                 sent, excluding the re-transmitted A11 Registration
                 Updates, since system was last restarted."
        REFERENCE
                 "Refer to TIA/EIA international telecommunications
                  organization standard TR 45.4 for A10 session update
                  message and TR 45.6 for Accounting Model."
        ::= { cCdmaRpUpdStats 5 }

cCdmaRpUpdReTransmittedReqs OBJECT-TYPE
        SYNTAX      Counter32
        MAX-ACCESS  read-only
        STATUS      current
        DESCRIPTION
                "Total number of re-transmitted A11 Registration
                 Updates, since system was last restarted."
        REFERENCE
                 "Refer to TIA/EIA international telecommunications
                  organization standard TR 45.4 for A10 session update
                  message and TR 45.6 for Accounting Model."
        ::= { cCdmaRpUpdStats 6 }

cCdmaRpUpdReceivedAcks OBJECT-TYPE
        SYNTAX      Counter32
        MAX-ACCESS  read-only
        STATUS      current
        DESCRIPTION
                "Total number of A11 Registration Acknowledgements
                 received, since system was last restarted. "
        REFERENCE
                 "Refer to TIA/EIA international telecommunications
                  organization standard TR 45.4 for A10 session update
                  message and TR 45.6 for Accounting Model."
        ::= { cCdmaRpUpdStats 7 }

cCdmaRpUpdDiscardedAcks OBJECT-TYPE
        SYNTAX      Counter32
        MAX-ACCESS  read-only
        STATUS      current
        DESCRIPTION
                "Total number of A11 Registration Acknowledgements
                 discarded, since system was last restarted."
        REFERENCE
                 "Refer to TIA/EIA international telecommunications
                  organization standard TR 45.4 for A10 session update

                  message and TR 45.6 for Accounting Model."
        ::= { cCdmaRpUpdStats 8 }

cCdmaRpUpdRpLifeExpReqs OBJECT-TYPE
        SYNTAX      Counter32
        MAX-ACCESS  read-only
        STATUS      current
        DESCRIPTION
                "Total number of initial A11 Registration Updates
                 sent due to RP lifetime expiry since system was
                 last restarted. Note that this count does not include
                 any retransmissions."
        REFERENCE
                 "Refer to TIA/EIA international telecommunications
                  organization standard TR 45.4 for A10 session update
                  message and TR 45.6 for Accounting Model."
        ::= { cCdmaRpUpdStats 9 }

cCdmaRpUpdPPPtermReqs OBJECT-TYPE
        SYNTAX      Counter32
        MAX-ACCESS  read-only
        STATUS      current
        DESCRIPTION
                "Total number of initial A11 Registration Updates
                 sent as a result of PPP termination, since system
                 was last restarted. Note that this count
                 does not include any retransmissions."
        REFERENCE
                 "Refer to TIA/EIA international telecommunications
                  organization standard TR 45.4 for A10 session update
                  message and TR 45.6 for Accounting Model."
        ::= { cCdmaRpUpdStats 10 }

cCdmaRpUpdOtherReasonReqs OBJECT-TYPE
        SYNTAX      Counter32
        MAX-ACCESS  read-only
        STATUS      current
        DESCRIPTION
                "Total number of initial A11 Registration Updates
                 sent due to reasons other than RP lifetime expiry,
                 or PPP termination, since system was last restarted.
                 Note that this count does not include any retransmissions."
        REFERENCE
                 "Refer to TIA/EIA international telecommunications
                  organization standard TR 45.4 for A10 session update
                  message and TR 45.6 for Accounting Model."
        ::= { cCdmaRpUpdStats 11 }

cCdmaRpUpdReasonUnSpecFailures OBJECT-TYPE
        SYNTAX      Counter32
        MAX-ACCESS  read-only
        STATUS      current
        DESCRIPTION
                "The number of update registrations failed for
                 unspecified reason since system was last restarted."
        REFERENCE
                 "Refer to TIA/EIA international telecommunications
                  organization standard TR 45.4 for details about A10
                  session setup errors."
        ::= { cCdmaRpUpdStats 12 }

cCdmaRpUpdAdminProhibFailures OBJECT-TYPE
        SYNTAX      Counter32
        MAX-ACCESS  read-only
        STATUS      current
        DESCRIPTION
                "The number of update registrations failed due to
                 administrative prohibition since system was last
                 restarted."
        REFERENCE
                 "Refer to TIA/EIA international telecommunications
                  organization standard TR 45.4 for details about A10
                  session setup errors."
        ::= { cCdmaRpUpdStats 13 }

cCdmaRpUpdMNAuthenFailures OBJECT-TYPE
        SYNTAX      Counter32
        MAX-ACCESS  read-only
        STATUS      current
        DESCRIPTION
                "The number of update registrations failed due to MN
                 authentication failure since system was last
                 restarted."
        REFERENCE
                 "Refer to TIA/EIA international telecommunications
                  organization standard TR 45.4 for details about A10
                  session setup errors."
        ::= { cCdmaRpUpdStats 14 }

cCdmaRpUpdIdentMismatchFailures OBJECT-TYPE
        SYNTAX      Counter32
        MAX-ACCESS  read-only
        STATUS      current
        DESCRIPTION
                "The number of registrations failed due to registration
                 identity mismatch since system was last restarted."
        REFERENCE
                 "Refer to TIA/EIA international telecommunications
                  organization standard TR 45.4 for details about A10
                  session setup errors."
        ::= { cCdmaRpUpdStats 15 }

cCdmaRpUpdBadReqFailures OBJECT-TYPE
        SYNTAX      Counter32
        MAX-ACCESS  read-only
        STATUS      current
        DESCRIPTION
                "The number of update registrations failed due to
                 poorly formed request since system was last restarted."
        REFERENCE
                 "Refer to TIA/EIA international telecommunications
                  organization standard TR 45.4 for details about A10
                  session setup errors."
        ::= { cCdmaRpUpdStats 16 }

cCdmaRpUpdPcfHandoffs OBJECT-TYPE
        SYNTAX      Counter32
        MAX-ACCESS  read-only
        STATUS      current
        DESCRIPTION
                "The number of update registrations sent as a 
                 result of inter pcf handoffs, since system was
                 last restarted."
        ::= { cCdmaRpUpdStats 17 }

cCdmaRpUpdHandoffNotAckedReqs OBJECT-TYPE
        SYNTAX      Counter32
        MAX-ACCESS  read-only
        STATUS      current
        DESCRIPTION
                "Total number of A11 Registration Updates (sent
                 as the result of inter PCF handoffs), for which no
                 corresponding A11  Registration Acknowledgements 
                 received, since system was last restarted."
        ::= { cCdmaRpUpdStats 18 }

cCdmaRpUpdHandoffReceivedAcks OBJECT-TYPE
        SYNTAX      Counter32
        MAX-ACCESS  read-only
        STATUS      current
        DESCRIPTION
                "Total number of A11 Registration Acknowledgements
                 received for the A11 Registration Updates sent as
                 the result of inter PCF handoffs, since system was
                 last restarted. "
        ::= { cCdmaRpUpdStats 19 }

cCdmaRpUpdHandoffAcceptedReqs OBJECT-TYPE
        SYNTAX      Counter32
        MAX-ACCESS  read-only
        STATUS      current
        DESCRIPTION
                "Total number of A11 Registration Acknowledgements
                 received with the Status field set to zero (indicating
                 that the corresponding Registration Update was
                 accepted), since system was last restarted."
        REFERENCE
                 "Refer to TIA/EIA international telecommunications
                  organization standard TR 45.4 for A10 session update
                  message and TR 45.6 for Accounting Model."
        ::= { cCdmaRpUpdStats 20 }

cCdmaRpUpdHandoffDeniedReqs OBJECT-TYPE
        SYNTAX      Counter32
        MAX-ACCESS  read-only
        STATUS      current
        DESCRIPTION
                "Total number of A11 Registration Acknowledgements
                 received with the Status field set to non-zero
                 indicating that the corresponding Registration Update
                 was denied, since system was last restarted."
        REFERENCE
                 "Refer to TIA/EIA international telecommunications
                  organization standard TR 45.4 for A10 session update
                  message and TR 45.6 for Accounting Model."
        ::= { cCdmaRpUpdStats 21 }

cCdmaRpUpdHandoffDiscardedAcks OBJECT-TYPE
        SYNTAX      Counter32
        MAX-ACCESS  read-only
        STATUS      current
        DESCRIPTION
                "Total number of A11 Registration Acknowledgements
                 discarded, since system was last restarted."
        ::= { cCdmaRpUpdStats 22 }
           
cCdmaRpUpdHandoffInitTxdReqs OBJECT-TYPE
        SYNTAX      Counter32
        MAX-ACCESS  read-only
        STATUS      current
        DESCRIPTION
                "Total number of initial A11 Registration Updates
                 sent as the result of inter PCF handoffs, excluding
                 the re-transmitted A11 Registration Updates, since
                 system was last restarted."
        ::= { cCdmaRpUpdStats 23 }

cCdmaRpUpdHandoffReTxdReqs OBJECT-TYPE
        SYNTAX      Counter32
        MAX-ACCESS  read-only
        STATUS      current
        DESCRIPTION
                "Total number of re-transmitted A11 Registration
                 Updates as the initial Registration Update (sent
                 as a result of inter PCF handoffs) was not acked
                 or denied, since system was last restarted."
        ::= { cCdmaRpUpdStats 24 }
            
cCdmaRpUpdHandoffReaUnSpecFails OBJECT-TYPE
        SYNTAX      Counter32
        MAX-ACCESS  read-only
        STATUS      current
        DESCRIPTION
                "The number of update registrations failed for
                 unspecified reason since system was last
                 restarted.  The update is sent as a result of
                 inter PCF handoff."
        ::= { cCdmaRpUpdStats 25 }
            
cCdmaRpUpdHandoffAdmProhibFails OBJECT-TYPE
        SYNTAX      Counter32
        MAX-ACCESS  read-only
        STATUS      current
        DESCRIPTION
                "The number of update registrations failed due to
                 administrative prohibition since system was last
                 restarted.  The update is sent as a result of
                 inter PCF handoff."
        ::= { cCdmaRpUpdStats 26 }

cCdmaRpUpdHandoffMNAuthenFails OBJECT-TYPE
        SYNTAX      Counter32
        MAX-ACCESS  read-only
        STATUS      current
        DESCRIPTION
                "The number of update registrations failed due 
                 to MN authentication failure since system was 
                 last restarted.  The update is sent as a result
                 of inter PCF handoff."
        ::= { cCdmaRpUpdStats 27 }
            
cCdmaRpUpdHandoffIdMismatchFails OBJECT-TYPE
        SYNTAX      Counter32
        MAX-ACCESS  read-only
        STATUS      current
        DESCRIPTION
                "The number of registrations failed due to registration
                 identity mismatch since system was last restarted.
                 The update is sent as a result of inter PCF handoff."
       ::= { cCdmaRpUpdStats 28 }
            
cCdmaRpUpdHandoffBadReqFails OBJECT-TYPE
        SYNTAX      Counter32
        MAX-ACCESS  read-only
        STATUS      current
        DESCRIPTION
                "The number of update registrations failed due to
                 poorly formed request since system was last 
                 restarted.  The update is sent as a result of inter
                 PCF handoff."
        ::= { cCdmaRpUpdStats 29 }

-- ******************************************************************
-- * CDMA PDSN Session Update Statistics
-- ******************************************************************

cCdmaRpSessUpdTransmittedReqs OBJECT-TYPE
        SYNTAX      ZeroBasedCounter32
        MAX-ACCESS  read-only
        STATUS      current
        DESCRIPTION
                "Total number of A11 Session Updates transmitted
                 since system was last restarted."
        REFERENCE
                 "Refer to TIA/EIA international telecommunications
                  organization standard TR 45.4 for A10 session update
                  message and TR 45.6 for Accounting Model."
        ::= { cCdmaRpSessUpdStats 1 }

cCdmaRpSessUpdAcceptedReqs OBJECT-TYPE
        SYNTAX      ZeroBasedCounter32
        MAX-ACCESS  read-only
        STATUS      current
        DESCRIPTION
                "Total number of A11 Session Update Acknowledgements
                 received with the Status field set to zero (indicating
                 that the corresponding Registration Update was
                 accepted), since system was last restarted."
        REFERENCE
                 "Refer to TIA/EIA international telecommunications
                  organization standard TR 45.4 for A10 session update
                  message and TR 45.6 for Accounting Model."
        ::= { cCdmaRpSessUpdStats 2 }

cCdmaRpSessUpdDeniedReqs OBJECT-TYPE
        SYNTAX      ZeroBasedCounter32
        MAX-ACCESS  read-only
        STATUS      current
        DESCRIPTION
                "Total number of A11 Session Update Acknowledgements
                 received with the Status field set to non-zero
                 indicating that the corresponding Registration Update
                 was denied, since system was last restarted."
        REFERENCE
                 "Refer to TIA/EIA international telecommunications
                  organization standard TR 45.4 for A10 session update
                  message and TR 45.6 for Accounting Model."
        ::= { cCdmaRpSessUpdStats 3 }

cCdmaRpSessUpdNotAckedReqs OBJECT-TYPE
        SYNTAX      ZeroBasedCounter32
        MAX-ACCESS  read-only
        STATUS      current
        DESCRIPTION
                "Total number of A11 Session Update Updates sent,
                 for which no corresponding A11 Registration
                 Acknowledgements received, since system was last
                 restarted."
        REFERENCE
                 "Refer to TIA/EIA international telecommunications
                  organization standard TR 45.4 for A10 session update
                  message and TR 45.6 for Accounting Model."
        ::= { cCdmaRpSessUpdStats 4 }

cCdmaRpSessUpdInitTransmittedReqs OBJECT-TYPE
        SYNTAX      ZeroBasedCounter32
        MAX-ACCESS  read-only
        STATUS      current
        DESCRIPTION
                "Total number of initial A11 Session Updates
                 sent, excluding the re-transmitted A11 Registration
                 Updates, since system was last restarted."
        REFERENCE
                 "Refer to TIA/EIA international telecommunications
                  organization standard TR 45.4 for A10 session update
                  message and TR 45.6 for Accounting Model."
        ::= { cCdmaRpSessUpdStats 5 }

cCdmaRpSessUpdReTransmittedReqs OBJECT-TYPE
        SYNTAX      ZeroBasedCounter32
        MAX-ACCESS  read-only
        STATUS      current
        DESCRIPTION
                "Total number of re-transmitted A11 Session
                 Updates, since system was last restarted."
        REFERENCE
                 "Refer to TIA/EIA international telecommunications
                  organization standard TR 45.4 for A10 session update
                  message and TR 45.6 for Accounting Model."
        ::= { cCdmaRpSessUpdStats 6 }

cCdmaRpSessUpdReceivedAcks OBJECT-TYPE
        SYNTAX      ZeroBasedCounter32
        MAX-ACCESS  read-only
        STATUS      current
        DESCRIPTION
                "Total number of A11 Session Update Acknowledgements
                 received, since system was last restarted. "
        REFERENCE
                 "Refer to TIA/EIA international telecommunications
                  organization standard TR 45.4 for A10 session update
                  message and TR 45.6 for Accounting Model."
        ::= { cCdmaRpSessUpdStats 7 }

cCdmaRpSessUpdDiscardedAcks OBJECT-TYPE
        SYNTAX      ZeroBasedCounter32
        MAX-ACCESS  read-only
        STATUS      current
        DESCRIPTION
                "Total number of A11 Session Update Acknowledgements
                 discarded, since system was last restarted."
        REFERENCE
                 "Refer to TIA/EIA international telecommunications
                  organization standard TR 45.4 for A10 session update

                  message and TR 45.6 for Accounting Model."
        ::= { cCdmaRpSessUpdStats 8 }

cCdmaRpSessUpdAlwaysON OBJECT-TYPE
        SYNTAX      ZeroBasedCounter32
        MAX-ACCESS  read-only
        STATUS      current
        DESCRIPTION
                "Total number of initial A11 Session Updates
                 sent due to Always On since system was
                 last restarted. Note that this count does not include
                 any retransmissions."
        REFERENCE
                 "Refer to TIA/EIA international telecommunications
                  organization standard TR 45.4 for A10 session update
                  message and TR 45.6 for Accounting Model."
        ::= { cCdmaRpSessUpdStats 9 }

cCdmaRpSessUpdRNPDIT OBJECT-TYPE
        SYNTAX      ZeroBasedCounter32
        MAX-ACCESS  read-only
        STATUS      current
        DESCRIPTION
                "Total number of initial A11 Registration Updates
                 sent due to RNPDIT value downloaded, since system
                 was last restarted. Note that this count
                 does not include any retransmissions."
        REFERENCE
                 "Refer to TIA/EIA international telecommunications
                  organization standard TR 45.4 for A10 session update
                  message and TR 45.6 for Accounting Model."
        ::= { cCdmaRpSessUpdStats 10 }

cCdmaRpSessUpdReasonUnSpecFailures OBJECT-TYPE
        SYNTAX      ZeroBasedCounter32
        MAX-ACCESS  read-only
        STATUS      current
        DESCRIPTION
                "The number of session update registrations failed for
                 unspecified reason since system was last restarted."
        REFERENCE
                 "Refer to TIA/EIA international telecommunications
                  organization standard TR 45.4 for details about A10
                  session setup errors."
        ::= { cCdmaRpSessUpdStats 11 }

cCdmaRpSessUpdReasonParamNotUpdated OBJECT-TYPE
        SYNTAX      ZeroBasedCounter32
        MAX-ACCESS  read-only
        STATUS      current
        DESCRIPTION
                "The number of session update registrations failed for
                 session parameters not updated reason since system was 
                 last restarted."
        REFERENCE
                 "Refer to TIA/EIA international telecommunications
                  organization standard TR 45.4 for details about A10
                  session setup errors."
        ::= { cCdmaRpSessUpdStats 12 }

cCdmaRpSessUpdMNAuthenFailures OBJECT-TYPE
        SYNTAX      ZeroBasedCounter32
        MAX-ACCESS  read-only
        STATUS      current
        DESCRIPTION
                "The number of session update registrations failed 
                 due to MN authentication failure since system was
                 last restarted."
        REFERENCE
                 "Refer to TIA/EIA international telecommunications
                  organization standard TR 45.4 for details about A10
                  session setup errors."
        ::= { cCdmaRpSessUpdStats 13 }

cCdmaRpSessUpdIdentMismatchFailures OBJECT-TYPE
        SYNTAX      ZeroBasedCounter32
        MAX-ACCESS  read-only
        STATUS      current
        DESCRIPTION
                "The number of session update registrations failed
                 due to registration identity mismatch since system
                 was last restarted."
        REFERENCE
                 "Refer to TIA/EIA international telecommunications
                  organization standard TR 45.4 for details about A10
                  session setup errors."
        ::= { cCdmaRpSessUpdStats 14 }

cCdmaRpSessUpdBadReqFailures OBJECT-TYPE
        SYNTAX      ZeroBasedCounter32
        MAX-ACCESS  read-only
        STATUS      current
        DESCRIPTION
                "The number of session update registrations failed due
                 to poorly formed request since system was last 
                 restarted."
        REFERENCE
                 "Refer to TIA/EIA international telecommunications
                  organization standard TR 45.4 for details about A10
                  session setup errors."
        ::= { cCdmaRpSessUpdStats 15 }

-- ******************************************************************
-- * CDMA PPP subgroup : cCdmaPppMiscStats is assigned 99 for
-- *                     future expansion
-- ******************************************************************
cCdmaPppSetupStats   OBJECT IDENTIFIER ::= { cCdmaPppStats 1 }
cCdmaPppReNegoStats  OBJECT IDENTIFIER ::= { cCdmaPppStats 2 }
cCdmaPppAuthStats    OBJECT IDENTIFIER ::= { cCdmaPppStats 3 }
cCdmaPppReleaseStats OBJECT IDENTIFIER ::= { cCdmaPppStats 4 }
cCdmaPppMiscStats    OBJECT IDENTIFIER ::= { cCdmaPppStats 99 }

-- ******************************************************************
-- * CDMA PPP SETUP subgroup counters
-- ******************************************************************

cCdmaPppCurrentConnections OBJECT-TYPE
        SYNTAX      Gauge32
        MAX-ACCESS  read-only
        STATUS      current
        DESCRIPTION
                "Total number of currently active PPP connections"
        REFERENCE
                 "Refer to PPP related RFC 1661, 1662, 1332, 1570, 1979
                  1962, 1974, 2509, 2661, 2716, 2284, 2118, 1994"
        ::= { cCdmaPppSetupStats 1 }

cCdmaPppConnectionInitiateReqs OBJECT-TYPE
        SYNTAX      Counter32
        MAX-ACCESS  read-only
        STATUS      current
        DESCRIPTION
                "Total number of PPP connection initiate requests
                 sent out since system was last restarted."
        REFERENCE
                 "Refer to PPP related RFC 1661, 1662, 1332, 1570, 1979
                  1962, 1974, 2509, 2661, 2716, 2284, 2118, 1994"
        ::= { cCdmaPppSetupStats 2 }

cCdmaPppConnectionSuccesses OBJECT-TYPE
        SYNTAX      Counter32
        MAX-ACCESS  read-only
        STATUS      current
        DESCRIPTION
                "Total number of PPP connections that have been successfully
                 brought to active state since system was last restarted."
        REFERENCE
                 "Refer to PPP related RFC 1661, 1662, 1332, 1570, 1979
                  1962, 1974, 2509, 2661, 2716, 2284, 2118, 1994"
        ::= { cCdmaPppSetupStats 3 }


cCdmaPppConnectionFailures OBJECT-TYPE
        SYNTAX      Counter32
        MAX-ACCESS  read-only
        STATUS      current
        DESCRIPTION
                "The number of PPP connection setup request failed since
                 system was last restarted."
        REFERENCE
                 "Refer to PPP related RFC 1661, 1662, 1332, 1570, 1979
                  1962, 1974, 2509, 2661, 2716, 2284, 2118, 1994"
        ::= { cCdmaPppSetupStats 4 }


cCdmaPppLcpFailures OBJECT-TYPE
        SYNTAX      Counter32
        MAX-ACCESS  read-only
        STATUS      current
        DESCRIPTION
                "Total number of PPP connection request that failed at LCP
                 stage since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 5 }


cCdmaPppAuthFailures OBJECT-TYPE
        SYNTAX      Counter32
        MAX-ACCESS  read-only
        STATUS      current
        DESCRIPTION
                "Total number of PPP Setup connections that failed at
                 authentication stage since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 6 }


cCdmaPppIpcpFailures OBJECT-TYPE
        SYNTAX      Counter32
        MAX-ACCESS  read-only
        STATUS      current
        DESCRIPTION
                "Total number of PPP Setup connections that failed at
                 IPCP stage since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 7 }

cCdmaPppEnterLcpNums OBJECT-TYPE
        SYNTAX      Counter32
        MAX-ACCESS  read-only
        STATUS      current
        DESCRIPTION
                "Total number of PPP connections entering LCP stage
                 since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 8 }


cCdmaPppEnterAuthNums OBJECT-TYPE
        SYNTAX      Counter32
        MAX-ACCESS  read-only
        STATUS      current
        DESCRIPTION
                "Total number of PPP connections entering authentication
                 stage since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 9 }


cCdmaPppEnterIpcpNums OBJECT-TYPE
        SYNTAX      Counter32
        MAX-ACCESS  read-only
        STATUS      current
        DESCRIPTION
                "Total number of PPP connections entering IPCP stage
                 since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 10 }

cCdmaPppLcpFailuresMaxRetrans OBJECT-TYPE
        SYNTAX      ZeroBasedCounter32
        MAX-ACCESS  read-only
        STATUS      current
        DESCRIPTION
                "Total number of PPP connection requests that failed at 
                 LCP stage after max number of retransmissions since
                 system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 11 }

cCdmaPppLcpFailuresUnknown OBJECT-TYPE
        SYNTAX      ZeroBasedCounter32
        MAX-ACCESS  read-only
        STATUS      current
        DESCRIPTION
                "Total number of PPP connection requests that failed at 
                 LCP stage due to an unknown reason since system was 
                 last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 12 }
        
cCdmaPppIpcpFailuresMaxRetrans OBJECT-TYPE
        SYNTAX      ZeroBasedCounter32
        MAX-ACCESS  read-only
        STATUS      current
        DESCRIPTION
                "Total number of PPP connection request that failed at 
                 IPCP stage after max number of retransmissions since
                 system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 13 }

cCdmaPppIpcpFailuresUnknown OBJECT-TYPE
        SYNTAX      ZeroBasedCounter32
        MAX-ACCESS  read-only
        STATUS      current
        DESCRIPTION
                "Total number of PPP connection requests that failed at 
                 IPCP stage due to an unknown reason since system was 
                 last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 14 }

cCdmaPppConnectionsAborted OBJECT-TYPE
        SYNTAX      ZeroBasedCounter32
        MAX-ACCESS  read-only
        STATUS      current
        DESCRIPTION
                "Total number of PPP negotiations terminated
                 prematurely due to reasons such as MN poweroff 
                 since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 15 }
        
cCdmaPppLcpOptionIssueFailures OBJECT-TYPE
        SYNTAX      ZeroBasedCounter32
        MAX-ACCESS  read-only
        STATUS      current
        DESCRIPTION
                "Total number of PPP connections terminated
                 due to LCP options negotiation failure such 
                 as call back user not negotiating the call back
                 option."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 16 }
        
cCdmaPppIpcpOptionIssueFailures OBJECT-TYPE
        SYNTAX      ZeroBasedCounter32
        MAX-ACCESS  read-only
        STATUS      current
        DESCRIPTION
                "Total number of PPP connections terminated
                 due to IPCP options negotiation failure such 
                 as ip address negotiation."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 17 }
  
cCdmaPppAuthMaxRetransFailures OBJECT-TYPE
        SYNTAX      ZeroBasedCounter32
        MAX-ACCESS  read-only
        STATUS      current
        DESCRIPTION
                "Total number of PPP connection requests that failed at
                 authentication stage after max number of
                 retransmissions since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 18 }
        
cCdmaPppNoRemoteIpAddressReleases OBJECT-TYPE
        SYNTAX      ZeroBasedCounter32
        MAX-ACCESS  read-only
        STATUS      current
        DESCRIPTION
                "Total number of PPP connections released because 
                 MN has no ip address as it rejects the IP address 
                 allocated by PDSN."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 19 }
        
cCdmaPppLowerLayerReleaseFailures OBJECT-TYPE
        SYNTAX      ZeroBasedCounter32
        MAX-ACCESS  read-only
        STATUS      current
        DESCRIPTION
                "Total number of PPP connections terminated
                 because the lower layer such as RP is disconnected." 
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 20 }
        
cCdmaPppIpcpPhaseReceivedTermreqs OBJECT-TYPE
        SYNTAX      ZeroBasedCounter32
        MAX-ACCESS  read-only
        STATUS      current
        DESCRIPTION
                "Total number of PPP negotiations terminated
                 due to PPP receiving term request during
                 the IPCP phase." 
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 21 }
        
cCdmaPppIpcpPhaseSentTermreqs OBJECT-TYPE
        SYNTAX      ZeroBasedCounter32
        MAX-ACCESS  read-only
        STATUS      current
        DESCRIPTION
                "Total number of PPP negotiations terminated
                 due to PPP sending term request during
                 the IPCP phase." 
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 22 }
        
cCdmaPppAuthPhaseReceivedTermreqs OBJECT-TYPE
        SYNTAX      ZeroBasedCounter32
        MAX-ACCESS  read-only
        STATUS      current
        DESCRIPTION
                "Total number of PPP negotiations terminated
                 due to PPP receiving term request during
                 the authentication phase." 
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 23 }
        
cCdmaPppAuthPhaseSentTermreqs OBJECT-TYPE
        SYNTAX      ZeroBasedCounter32
        MAX-ACCESS  read-only
        STATUS      current
        DESCRIPTION
                "Total number of PPP negotiations terminated
                 due to PPP sending term request during
                 the authentication phase." 
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 24 }
        
cCdmaPppLcpPhaseReceivedTermreqs OBJECT-TYPE
        SYNTAX      ZeroBasedCounter32
        MAX-ACCESS  read-only
        STATUS      current
        DESCRIPTION
                "Total number of PPP negotiations terminated
                 due to PPP receiving term request during
                 the LCP phase." 
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 25 }
        
cCdmaPppLcpPhaseSentTermreqs OBJECT-TYPE
        SYNTAX      ZeroBasedCounter32
        MAX-ACCESS  read-only
        STATUS      current
        DESCRIPTION
                "Total number of PPP negotiations terminated
                 due to PPP sending term request during
                 the LCP phase." 
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 26 }

cCdmaPppPreLCPPdsnA10Releases OBJECT-TYPE
        SYNTAX      ZeroBasedCounter32
        MAX-ACCESS  read-only
        STATUS      current
        DESCRIPTION
                "Total number of A10 connections released
                 by PDSN before the PPP enters LCP negotiation phase."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 27 }
        
cCdmaPppPreLCPPcfA10Releases OBJECT-TYPE
        SYNTAX      ZeroBasedCounter32
        MAX-ACCESS  read-only
        STATUS      current
        DESCRIPTION
                "Total number of A10 connections released
                 by PCF before the PPP enters LCP negotiation phase."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 28 }
        
cCdmaPppLCPPdsnA10Releases OBJECT-TYPE
        SYNTAX      ZeroBasedCounter32
        MAX-ACCESS  read-only
        STATUS      current
        DESCRIPTION
                "Total number of A10 connections released
                 by PDSN during the LCP negotiation phase."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 29 }
        
cCdmaPppLCPPcfA10Releases OBJECT-TYPE
        SYNTAX      ZeroBasedCounter32
        MAX-ACCESS  read-only
        STATUS      current
        DESCRIPTION
                "Total number of A10 connections released
                 by PCF during the LCP negotiation phase."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 30 }
        
cCdmaPppAuthPdsnA10Releases OBJECT-TYPE
        SYNTAX      ZeroBasedCounter32
        MAX-ACCESS  read-only
        STATUS      current
        DESCRIPTION
                "Total number of A10 connections released
                 by PDSN during the PPP authentication phase."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 31 }
        
cCdmaPppAuthPcfA10Releases OBJECT-TYPE
        SYNTAX      ZeroBasedCounter32
        MAX-ACCESS  read-only
        STATUS      current
        DESCRIPTION
                "Total number of A10 connections released
                 by PCF during the PPP authentication phase."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 32 }
        
cCdmaPppIPCPPdsnA10Releases OBJECT-TYPE
        SYNTAX      ZeroBasedCounter32
        MAX-ACCESS  read-only
        STATUS      current
        DESCRIPTION
                "Total number of A10 connections released
                 by PDSN during the IPCP negotiation phase."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 33 }
        
cCdmaPppIPCPPcfA10Releases OBJECT-TYPE
        SYNTAX      ZeroBasedCounter32
        MAX-ACCESS  read-only
        STATUS      current
        DESCRIPTION
                "Total number of A10 connections released
                 by PCF during the IPCP negotiation phase."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 34 }

cCdmaPppLcpSuccesses OBJECT-TYPE
        SYNTAX      ZeroBasedCounter32
        MAX-ACCESS  read-only
        STATUS      current
        DESCRIPTION
                "Total number of PPP connections that entered
                 LCP stage successfully."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 35 }
        
cCdmaPppIpcpSuccesses OBJECT-TYPE
        SYNTAX      ZeroBasedCounter32
        MAX-ACCESS  read-only
        STATUS      current
        DESCRIPTION
                "Total number of PPP connections that entered
                 IPCP stage successfully."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 36 }
        
cCdmaPppAuthSuccesses OBJECT-TYPE
        SYNTAX      ZeroBasedCounter32
        MAX-ACCESS  read-only
        STATUS      current
        DESCRIPTION
                "Total number of PPP connections that succeeded
                 authentication."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 37 }
        
cCdmaPppConnectionOtherFailures OBJECT-TYPE
        SYNTAX      ZeroBasedCounter32
        MAX-ACCESS  read-only
        STATUS      current
        DESCRIPTION
                "Total number of PPP negotiations terminated
                 due to miscellaneous reasons."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppSetupStats 38 }

-- *******************************************************************

-- PDSN PPP Re-Negotiation subgroup counters
--********************************************************************
cCdmaPppRenegTotalReqs OBJECT-TYPE
        SYNTAX      Counter32
        MAX-ACCESS  read-only
        STATUS      current
        DESCRIPTION
                "Total number of PPP connections renegotiated by either
                 PDSN or mobile node since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppReNegoStats 1 }


cCdmaPppRenegByPdsnReqs OBJECT-TYPE
        SYNTAX      Counter32
        MAX-ACCESS  read-only
        STATUS      current
        DESCRIPTION
                "Total number of PPP connection renegotiation requests 
                 initiated by PDSN  since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppReNegoStats 2 }


cCdmaPppRenegByMobileReqs OBJECT-TYPE
        SYNTAX      Counter32
        MAX-ACCESS  read-only
        STATUS      current
        DESCRIPTION
                "Total number of PPP connection renegotiations requests 
                 initiated by mobile node since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppReNegoStats 3 }

cCdmaPppRenegLcpIpcpReqs OBJECT-TYPE
        SYNTAX      Counter32
        MAX-ACCESS  read-only
        STATUS      current
        DESCRIPTION
             "Total Number of PPP connection renegotiate request sent 
              during setup (LCP and IPCP stages) since PDSN was last
              restarted."
        REFERENCE
                 "Refer to PPP related RFC 1661, 1662, 1332, 1570, 1979
                  1962, 1974, 2509, 2661, 2716, 2284, 2118, 1994"
        ::= { cCdmaPppReNegoStats 4 }

cCdmaPppRenegAddrMismatchReqs OBJECT-TYPE
        SYNTAX      Counter32
        MAX-ACCESS  read-only
        STATUS      current
        DESCRIPTION
                "Total number of PPP connections renegotiated due to ip
                 address mismatch since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppReNegoStats 5 }


cCdmaPppRenegOtherReasonReqs OBJECT-TYPE
        SYNTAX      Counter32
        MAX-ACCESS  read-only
        STATUS      current
        DESCRIPTION
                "Total number of PPP connections renegotiated due to
                 reasons other than IP address mismatch since system was
                 last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppReNegoStats 10 }

cCdmaPppRenegSuccesses OBJECT-TYPE
        SYNTAX      ZeroBasedCounter32
        MAX-ACCESS  read-only
        STATUS      current
        DESCRIPTION
                "Total number of PPP re-negotiations that have been 
                 successfully brought to active state since system 
                 was last restarted."
        REFERENCE
                 "Refer to PPP related RFC 1661, 1662, 1332, 1570, 1979
                  1962, 1974, 2509, 2661, 2716, 2284, 2118, 1994"
        ::= { cCdmaPppReNegoStats 11 }

cCdmaPppRenegFailures OBJECT-TYPE
        SYNTAX      ZeroBasedCounter32
        MAX-ACCESS  read-only
        STATUS      current
        DESCRIPTION
                "Total number of PPP re-negotiations failed since
                 system was last restarted."
        REFERENCE
                 "Refer to PPP related RFC 1661, 1662, 1332, 1570, 1979
                  1962, 1974, 2509, 2661, 2716, 2284, 2118, 1994"
        ::= { cCdmaPppReNegoStats 12 }
        
cCdmaPppRenegConnectionsAborted OBJECT-TYPE
        SYNTAX      ZeroBasedCounter32
        MAX-ACCESS  read-only
        STATUS      current
        DESCRIPTION
                "Total number of PPP re-negotiations terminated
                 prematurely due to reasons such as MN poweroff etc."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppReNegoStats 13 }

cCdmaPppRenegAnidChanges OBJECT-TYPE
        SYNTAX      ZeroBasedCounter32
        MAX-ACCESS  read-only
        STATUS      current
        DESCRIPTION
                "Total number of PPP connections renegotiated due to
                 access-network id(anid) change during session 
                 handoff." 
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppReNegoStats 14 }

-- ************************************************************************
-- PDSN PPP authentication subgroup counters
-- ************************************************************************

cCdmaPppAuthChapAttempts OBJECT-TYPE
        SYNTAX      Counter32
        MAX-ACCESS  read-only
        STATUS      current
        DESCRIPTION
                "Total number of PPP CHAP authentication requests sent
                 out since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppAuthStats 1 }


cCdmaPppAuthChapSuccesses OBJECT-TYPE
        SYNTAX      Counter32
        MAX-ACCESS  read-only
        STATUS      current
        DESCRIPTION
                "Total number of PPP CHAP authentication successes
                 since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppAuthStats 2 }


cCdmaPppAuthChapFailures OBJECT-TYPE
        SYNTAX      Counter32
        MAX-ACCESS  read-only
        STATUS      current
        DESCRIPTION
                "Total number of PPP CHAP authentication failures
                 since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppAuthStats 3 }


cCdmaPppAuthPapAttempts OBJECT-TYPE
        SYNTAX      Counter32
        MAX-ACCESS  read-only
        STATUS      current
        DESCRIPTION
                "Total number of PPP PAP authentication requests sent
                 out since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppAuthStats 4 }


cCdmaPppAuthPapSuccesses OBJECT-TYPE
        SYNTAX      Counter32
        MAX-ACCESS  read-only
        STATUS      current
        DESCRIPTION
                "Total number of PPP PAP authentication successes since
                 system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppAuthStats 5 }


cCdmaPppAuthPapFailures OBJECT-TYPE
        SYNTAX      Counter32
        MAX-ACCESS  read-only
        STATUS      current
        DESCRIPTION
                "Total number of PPP PAP authentication failures since
                 system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppAuthStats 6 }


cCdmaPppAuthMschapAttempts OBJECT-TYPE
        SYNTAX      Counter32
        MAX-ACCESS  read-only
        STATUS      current
        DESCRIPTION
                "Total number of PPP MSCHAP authentication requests
                 sent out since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppAuthStats 7 }

cCdmaPppAuthMschapSuccesses OBJECT-TYPE
        SYNTAX      Counter32
        MAX-ACCESS  read-only
        STATUS      current
        DESCRIPTION
                "Total number of PPP MSCHAP authentication successes
                 since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppAuthStats 8 }


cCdmaPppAuthMschapFailures OBJECT-TYPE
        SYNTAX      Counter32
        MAX-ACCESS  read-only
        STATUS      current
        DESCRIPTION
                "Total number of PPP MSCHAP authentication failures
                 since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppAuthStats 9 }


cCdmaPppAuthEapAttempts OBJECT-TYPE
        SYNTAX      Counter32
        MAX-ACCESS  read-only
        STATUS      current
        DESCRIPTION
                "Total number of PPP EAP authentication requests sent
                 out since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppAuthStats 10 }


cCdmaPppAuthEapSuccesses OBJECT-TYPE
        SYNTAX      Counter32
        MAX-ACCESS  read-only
        STATUS      current
        DESCRIPTION
                "Total number of PPP EAP authentication successes
                 since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppAuthStats 11 }


cCdmaPppAuthEapFailures OBJECT-TYPE
        SYNTAX      Counter32
        MAX-ACCESS  read-only
        STATUS      current
        DESCRIPTION
                "Total number of PPP EAP authentication failures since
                 system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppAuthStats 12 }

cCdmaPppAuthMsidAttempts OBJECT-TYPE
        SYNTAX      Counter32
        MAX-ACCESS  read-only
        STATUS      current
        DESCRIPTION
                "Total number of PPP MSID authentication requests tried
                 since system was last restarted."
        ::= { cCdmaPppAuthStats 13 }

cCdmaPppAuthMsidSuccesses OBJECT-TYPE
        SYNTAX      Counter32
        MAX-ACCESS  read-only
        STATUS      current
        DESCRIPTION
                "Total number of PPP MSID authentication successes
                 since system was last restarted."
        ::= { cCdmaPppAuthStats 14 }

cCdmaPppAuthMsidFailures OBJECT-TYPE
        SYNTAX      Counter32
        MAX-ACCESS  read-only
        STATUS      current
        DESCRIPTION
                "Total number of PPP MSID authentication failures since
                 system was last restarted."
        ::= { cCdmaPppAuthStats 15 }

cCdmaPppAuthAAATimeouts OBJECT-TYPE
        SYNTAX      Counter32
        MAX-ACCESS  read-only
        STATUS      current
        DESCRIPTION
                "Total number of PPP authentication failures due to 
                 AAA timeouts, since system was last restarted."
        ::= { cCdmaPppAuthStats 16 }

cCdmaPppAuthChapTimeouts OBJECT-TYPE
        SYNTAX      ZeroBasedCounter32
        MAX-ACCESS  read-only
        STATUS      current
        DESCRIPTION
                "Total number of PPP CHAP authentication timeouts as
                 MN does not respond to CHAP request, since system was 
                 last restarted."
        ::= { cCdmaPppAuthStats 17 }

cCdmaPppAuthPapTimeouts OBJECT-TYPE
        SYNTAX      ZeroBasedCounter32
        MAX-ACCESS  read-only
        STATUS      current
        DESCRIPTION
                "Total number of PPP PAP authentication timeouts as
                 MN does not send PAP request, since system was 
                 last restarted."
        ::= { cCdmaPppAuthStats 18 }

cCdmaPppAuthMschapTimeouts OBJECT-TYPE
        SYNTAX      ZeroBasedCounter32
        MAX-ACCESS  read-only
        STATUS      current
        DESCRIPTION
                "Total number of PPP MSCHAP authentication timeouts as
                 MN does not respond to MSCHAP request, since system was 
                 last restarted."
        ::= { cCdmaPppAuthStats 19 }

cCdmaPppAuthSkips OBJECT-TYPE
        SYNTAX      ZeroBasedCounter32
        MAX-ACCESS  read-only
        STATUS      current
        DESCRIPTION
                "Total number of PPP negotiations that skipped PPP
                 authentication, since system was last restarted."
        ::= { cCdmaPppAuthStats 20 }

-- **********************************************************************
-- PDSN PPP connection release subgroup
-- **********************************************************************
cCdmaPppTotalReleases OBJECT-TYPE
        SYNTAX      Counter32
        MAX-ACCESS  read-only
        STATUS      current
        DESCRIPTION
                "Total number of active PPP connections released by either
                 PDSN or mobile node since system was last restarted."
        REFERENCE
                 "Refer to PPP related RFC 1661, 1662, 1332, 1570, 1979
                  1962, 1974, 2509, 2661, 2716, 2284, 2118, 1994"
        ::= { cCdmaPppReleaseStats 1 }


cCdmaPppPdsnReleases OBJECT-TYPE
        SYNTAX      Counter32
        MAX-ACCESS  read-only
        STATUS      current
        DESCRIPTION
                "Total number of active PPP connection release
                 request initiated by the PDSN since system was
                 last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppReleaseStats 2 }


cCdmaPppMobileReleases OBJECT-TYPE
        SYNTAX      Counter32
        MAX-ACCESS  read-only
        STATUS      current
        DESCRIPTION
                "Total number of active PPP connection release request
                 initiated by mobile node since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppReleaseStats 3 }

cCdmaPppAddrFilterReleases OBJECT-TYPE
        SYNTAX      Counter32
        MAX-ACCESS  read-only
        STATUS      current
        DESCRIPTION
                "Total number of PPP connection release due to ingress address
                 filering since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppReleaseStats 4 }

cCdmaPppAdminReleases OBJECT-TYPE
        SYNTAX      Counter32
        MAX-ACCESS  read-only
        STATUS      current
        DESCRIPTION
                "Total number of PPP connections released due to
                 administrative command  since system was last restarted"
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppReleaseStats 5 }


cCdmaPppLcpTermReleases OBJECT-TYPE
        SYNTAX      Counter32
        MAX-ACCESS  read-only
        STATUS      deprecated
        DESCRIPTION
                "Total number of PPP connections released due to LCP Term 
                 REQ since system was last restarted."
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppReleaseStats 6 }


cCdmaPppIdleTimeoutReleases OBJECT-TYPE
        SYNTAX      Counter32
        MAX-ACCESS  read-only
        STATUS      current
        DESCRIPTION
                "Total number of PPP connections released because of
                 PPP idle timeout since system was last restarted."
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppReleaseStats 7 }


cCdmaPppL2tpTunnelReleases OBJECT-TYPE
        SYNTAX      Counter32
        MAX-ACCESS  read-only
        STATUS      current
        DESCRIPTION
                "Total number of PPP connections released due to L2TP
                 tunnel release since system was last restarted."
        REFERENCE
                 "Refer to TIA/EIA international telecommunications
                  organization standard TR 45.4 for A11/A10 interface

                  and PPP related RFC 1661, 1662, 1332, 1570, 1979
                  1962,1990, 1974, 2509, 2661, 2716, 2284, 2118, 1994"
        ::= { cCdmaPppReleaseStats 8 }


cCdmaPppInsufResReleases OBJECT-TYPE
        SYNTAX      Counter32
        MAX-ACCESS  read-only
        STATUS      deprecated
        DESCRIPTION
                "Total number of PPP connections released due to
                 insufficient resources since system was last
                 restarted."
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppReleaseStats 9 }


cCdmaPppSessTimeoutReleases OBJECT-TYPE
        SYNTAX      Counter32
        MAX-ACCESS  read-only
        STATUS      current
        DESCRIPTION
                "Total number of PPP connections released due to
                 session timeout since system was last restarted."
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppReleaseStats 10 }


cCdmaPppSrvIntReleases OBJECT-TYPE
        SYNTAX      Counter32
        MAX-ACCESS  read-only
        STATUS      current
        DESCRIPTION
                "Total number of PPP connections released due to
                 service interruption since system was last restarted."
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppReleaseStats 11 }


cCdmaPppSrvUnavailReleases OBJECT-TYPE
        SYNTAX      Counter32
        MAX-ACCESS  read-only
        STATUS      current
        DESCRIPTION
                "Total number of PPP connections released due to
                 service unavailable since system was last
                 restarted."
        REFERENCE
                 "Refer to TIA/EIA international telecommunications
                  organization standard TR 45.4 for A11/A10 interface
                  and PPP related RFC 1661, 1662, 1332, 1570, 1979
                  1962,1990, 1974, 2509, 2661, 2716, 2284, 2118, 1994"
        ::= {  cCdmaPppReleaseStats 12 }

cCdmaPppMissEchoReleases OBJECT-TYPE
        SYNTAX      Counter32
        MAX-ACCESS  read-only
        STATUS      current
        DESCRIPTION
                "Total number of PPP connections released as peer
                 did not send echo reply to echo requests since
                 system was last restarted."
        REFERENCE
                 "Refer to TIA/EIA international telecommunications
                  organization standard TR 45.4 for A11/A10 interface
                  and PPP related RFC 1661, 1662, 1332, 1570, 1979
                  1962,1990, 1974, 2509, 2661, 2716, 2284, 2118, 1994"
        ::= {  cCdmaPppReleaseStats 13 }

cCdmaPppDeregisterByPcfReleases OBJECT-TYPE
        SYNTAX      ZeroBasedCounter32
        MAX-ACCESS  read-only
        STATUS      current
        DESCRIPTION
                "Total number of PPP connections released as pcf
                 sends deregistration request since system was 
                 last restarted."
        REFERENCE
                 "Refer to TIA/EIA international telecommunications
                  organization standard TR 45.4 for A11/A10 interface
                  and PPP related RFC 1661, 1662, 1332, 1570, 1979
                  1962,1990, 1974, 2509, 2661, 2716, 2284, 2118, 1994"
        ::= {  cCdmaPppReleaseStats 14 }

cCdmaPppLifetimeExpiryReleases OBJECT-TYPE
        SYNTAX      ZeroBasedCounter32
        MAX-ACCESS  read-only
        STATUS      current
        DESCRIPTION
                "Total number of PPP connections released as the session
                 lifetime expires, since the system was last restarted."
        REFERENCE
                 "Refer to TIA/EIA international telecommunications
                  organization standard TR 45.4 for A11/A10 interface
                  and PPP related RFC 1661, 1662, 1332, 1570, 1979
                  1962,1990, 1974, 2509, 2661, 2716, 2284, 2118, 1994"
        ::= {  cCdmaPppReleaseStats 15 }

cCdmaPppOtherReasonReleases OBJECT-TYPE
        SYNTAX      Counter32
        MAX-ACCESS  read-only
        STATUS      current
        DESCRIPTION
                "Total number of PPP connections released due to unknown
                 reasons since system was last restarted."
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppReleaseStats 99 }

-- ************************************************************************
-- PDSN PPP other counters (other than previous four  subgroup)
-- ************************************************************************
cCdmaPppCompressNegoCons OBJECT-TYPE
        SYNTAX      Counter32
        MAX-ACCESS  read-only
        STATUS      current
        DESCRIPTION
                "Total number of PPP connections that negotiated compression
                 since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppMiscStats 1 }


cCdmaPppCompressMsftCons OBJECT-TYPE
        SYNTAX      Counter32
        MAX-ACCESS  read-only
        STATUS      current
        DESCRIPTION
                "Total number of PPP connections that use Microsoft
                 compression since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppMiscStats 2 }

cCdmaPppCompressAscendCons OBJECT-TYPE
        SYNTAX      Counter32
        MAX-ACCESS  read-only
        STATUS      current
        DESCRIPTION
                "Total number of PPP connections that use Ascend compression
                 since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppMiscStats 3 }

cCdmaPppCompressStackCons OBJECT-TYPE
        SYNTAX      Counter32
        MAX-ACCESS  read-only
        STATUS      current
        DESCRIPTION
                "Total number of PPP connections that use stack compression
                 since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppMiscStats 4 }


cCdmaPppCompressDeflateCons OBJECT-TYPE
        SYNTAX      Counter32
        MAX-ACCESS  read-only
        STATUS      current
        DESCRIPTION
                "Total number of PPP connections that use deflate compression
                 since system was last restarted. "
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppMiscStats 5 }


cCdmaPppCompressOtherCons OBJECT-TYPE
        SYNTAX      Counter32
        MAX-ACCESS  read-only
        STATUS      current
        DESCRIPTION
                "Total number of PPP connections that use compression type
                 other than above since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppMiscStats 10 }

cCdmaPppNegoMrruCons OBJECT-TYPE
        SYNTAX      Counter32
        MAX-ACCESS  read-only
        STATUS      current
        DESCRIPTION
                "Total number of PPP connections that have negotiated MRRU
                 since system was last restarted. "
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppMiscStats 11 }


cCdmaPppNegoIpxCons OBJECT-TYPE
        SYNTAX      Counter32
        MAX-ACCESS  read-only
        STATUS      current
        DESCRIPTION
                "Total number of PPP connections that have negotiated IPX
                 protocol since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppMiscStats 12 }


cCdmaPppNegoIpCons OBJECT-TYPE
        SYNTAX      Counter32
        MAX-ACCESS  read-only
        STATUS      current
        DESCRIPTION
                "Total number of PPP connections that have negotiated
                 IP protocol since system was last restarted."
        REFERENCE
                 "Refer to TIA/EIA international telecommunications
                  organization standard TR 45.4 for A11/A10 interface
                  and PPP related RFC 1661, 1662, 1332, 1570, 1979
                  1962, 1974, 2509, 2661, 2716, 2284, 2118, 1994"
        ::= { cCdmaPppMiscStats 13 }

cCdmaPppNegoVjCompCons OBJECT-TYPE
        SYNTAX      Counter32
        MAX-ACCESS  read-only
        STATUS      current
        DESCRIPTION
                "Total number of PPP connections that have negotiated header
                 VJ-Compression since system was last restarted."
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppMiscStats 14 }


cCdmaPppNegoBapCons OBJECT-TYPE
        SYNTAX      Counter32
        MAX-ACCESS  read-only
        STATUS      current
        DESCRIPTION
                "Total number of PPP connections that negotiated BAP (Bandwidth 
                 Allocation protocol, RFC 2125) since system was last restarted."
        REFERENCE
                 "Refer to TIA/EIA international telecommunications
                  organization standard TR 45.4 for A11/A10 interface
                  and PPP related RFC 1661, 1662, 1332, 1570, 1979, 2125,
                  1962,1990, 1974, 2509, 2661, 2716, 2284, 2118, 1994"
        ::= { cCdmaPppMiscStats 15 }


cCdmaPppConFormedBundles OBJECT-TYPE
        SYNTAX      Counter32
        MAX-ACCESS  read-only
        STATUS      current
        DESCRIPTION
                "Total number of PPP bundles formed since system was
                 last restarted. "
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppMiscStats 16 }

cCdmaPppCompressNegoFailures OBJECT-TYPE
        SYNTAX      ZeroBasedCounter32
        MAX-ACCESS  read-only
        STATUS      current
        DESCRIPTION
                "Total number of PPP negotiations that failed due to
                 compression negotiation failure, since the system was
                 last restarted. "
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppMiscStats 17 }

cCdmaPppTransmittedEchoReqs OBJECT-TYPE
        SYNTAX      ZeroBasedCounter32
        MAX-ACCESS  read-only
        STATUS      current
        DESCRIPTION
                "Total number of LCP Echo requests transmitted,
                 since system was last restarted. "
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppMiscStats 18 }

cCdmaPppRetransmittedEchoReqs OBJECT-TYPE
        SYNTAX      ZeroBasedCounter32
        MAX-ACCESS  read-only
        STATUS      current
        DESCRIPTION
                "Total number of LCP Echo requests retransmitted,
                 since system was last restarted. "
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppMiscStats 19 }

cCdmaPppReceivedEchoReplies OBJECT-TYPE
        SYNTAX      ZeroBasedCounter32
        MAX-ACCESS  read-only
        STATUS      current
        DESCRIPTION
                "Total number of LCP Echo reply received,
                 since system was last restarted. "
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppMiscStats 20 }

cCdmaPppEchoRequestTimeouts OBJECT-TYPE
        SYNTAX      ZeroBasedCounter32
        MAX-ACCESS  read-only
        STATUS      current
        DESCRIPTION
                "Total number of LCP Echo requests timed out,
                 since system was last restarted. "
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppMiscStats 21 }

cCdmaPppUnknownProtocolPktDiscards OBJECT-TYPE
        SYNTAX      ZeroBasedCounter32
        MAX-ACCESS  read-only
        STATUS      current
        DESCRIPTION
                "Total number of packets discarded at PPP stack due to
                 protocol value can not be identified, since the system
                 was last restarted. "
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppMiscStats 22 }

cCdmaPppBadLengthPktDiscards OBJECT-TYPE
        SYNTAX      ZeroBasedCounter32
        MAX-ACCESS  read-only
        STATUS      current
        DESCRIPTION
                "Total number of PPP packets discarded stack due to
                 bad length, since the system was last restarted. "
        REFERENCE
                 "Refer to TIA/EIA international telecommunications
                  organization standard TR 45.4 for A11/A10 interface
                  and PPP related RFC 1661, 1662, 1332, 1570, 1979
                  1962,1990, 1974, 2509, 2661, 2716, 2284, 2118, 1994"
        ::= { cCdmaPppMiscStats 23 }

-- ******************************************************************
-- * CDMA Service Level (Simple IP, Mobile IP, and Proxy Mobile IP)
-- * Traffic Statistics
-- ******************************************************************

cCdmaTransmittedSipKiloOctets OBJECT-TYPE
        SYNTAX      Counter32
        MAX-ACCESS  read-only
        STATUS      current
        DESCRIPTION
                "Total number of simple IP data octets (in unit of 1024 octets) 
                 sent to mobile stations from PDSN since system was last 
                 restarted."
        REFERENCE
                 "Refer to TIA/EIA international telecommunications
                  organization standard TR 45.4 for A10 session update
                  message and TR 45.6 for Accounting Model."
        ::= { cCdmaTrafficStats 1 }

cCdmaReceivedSipKiloOctets OBJECT-TYPE
        SYNTAX      Counter32
        MAX-ACCESS  read-only
        STATUS      current
        DESCRIPTION
                "Total number of simple IP data octets (in unit of 1024 octets) 
                 received from mobile stations by PDSN since system was last 
                 restarted."
        REFERENCE
                 "Refer to TIA/EIA international telecommunications
                  organization standard TR 45.4 for A10 session update
                  message and TR 45.6 for Accounting Model."
        ::= { cCdmaTrafficStats 2 }

cCdmaTransmittedSipPkts OBJECT-TYPE
        SYNTAX      Counter32
        MAX-ACCESS  read-only
        STATUS      current
        DESCRIPTION
                "Total number of simple IP data packets sent to mobile stations 
                 since system was last restarted."
        REFERENCE
                 "Refer to TIA/EIA international telecommunications
                  organization standard TR 45.4 for A10 session update
                  message and TR 45.6 for Accounting Model."
        ::= { cCdmaTrafficStats 3 }

cCdmaReceivedSipPkts OBJECT-TYPE
        SYNTAX      Counter32
        MAX-ACCESS  read-only
        STATUS      current
        DESCRIPTION
                "Total number of simple IP data packets received from mobile 
                 stations since system was last restarted."
        REFERENCE
                 "Refer to TIA/EIA international telecommunications
                  organization standard TR 45.4 for A10 session update
                  message and TR 45.6 for Accounting Model."
        ::= { cCdmaTrafficStats 4 }

cCdmaTransmittedMipKiloOctets OBJECT-TYPE
        SYNTAX      Counter32
        MAX-ACCESS  read-only
        STATUS      current
        DESCRIPTION
                "Total number of mobile IP data octets (in unit of 1024 octets) 
                 sent to mobile stations from PDSN since system was last 
                 restarted."
        REFERENCE
                 "Refer to TIA/EIA international telecommunications
                  organization standard TR 45.4 for A10 session update
                  message and TR 45.6 for Accounting Model."
        ::= { cCdmaTrafficStats 5 }

cCdmaReceivedMipKiloOctets OBJECT-TYPE
        SYNTAX      Counter32
        MAX-ACCESS  read-only
        STATUS      current
        DESCRIPTION
                "Total number of mobile IP data octets (in unit of 1024 octets) 
                 received from mobile stations by PDSN since system was last 
                 restarted."
        REFERENCE
                 "Refer to TIA/EIA international telecommunications
                  organization standard TR 45.4 for A10 session update
                  message and TR 45.6 for Accounting Model."
        ::= { cCdmaTrafficStats 6 }

cCdmaTransmittedMipPkts OBJECT-TYPE
        SYNTAX      Counter32
        MAX-ACCESS  read-only
        STATUS      current
        DESCRIPTION
                "Total number of mobile IP data packets sent to mobile stations 
                 from PDSN since system was last restarted."
        REFERENCE
                 "Refer to TIA/EIA international telecommunications
                  organization standard TR 45.4 for A10 session update
                  message and TR 45.6 for Accounting Model."
        ::= { cCdmaTrafficStats 7 }

cCdmaReceivedMipPkts OBJECT-TYPE
        SYNTAX      Counter32
        MAX-ACCESS  read-only
        STATUS      current
        DESCRIPTION
                "Total number of mobile IP data packets received from mobile 
                 stations since system was last restarted."
        REFERENCE
                 "Refer to TIA/EIA international telecommunications
                  organization standard TR 45.4 for A10 session update
                  message and TR 45.6 for Accounting Model."
        ::= { cCdmaTrafficStats 8 }

cCdmaTransmittedPmipKiloOctets OBJECT-TYPE
        SYNTAX      Counter32
        MAX-ACCESS  read-only
        STATUS      current
        DESCRIPTION
                "Total number of proxy mobile IP data octets (in unit of 1024 
                 octets) sent to mobile stations from PDSN since system was
                 last restarted."
        REFERENCE
                 "Refer to TIA/EIA international telecommunications
                  organization standard TR 45.4 for A10 session update
                  message and TR 45.6 for Accounting Model and CISCO PDSN 
                  release note."
        ::= { cCdmaTrafficStats 9 }

cCdmaReceivedPmipKiloOctets OBJECT-TYPE
        SYNTAX      Counter32
        MAX-ACCESS  read-only
        STATUS      current
        DESCRIPTION
                "Total number of proxy mobile IP data octets (in unit of 1024 
                 octets) received from mobile stations  since system was last
                 restarted."
        REFERENCE
                 "Refer to TIA/EIA international telecommunications
                  organization standard TR 45.4 for A10 session update
                  message and TR 45.6 for Accounting Model and CISCO PDSN 
                  release note."
        ::= { cCdmaTrafficStats 10 }

cCdmaTransmittedPmipPkts OBJECT-TYPE
        SYNTAX      Counter32
        MAX-ACCESS  read-only
        STATUS      current
        DESCRIPTION
                "Total number of proxy mobile IP data packets sent to mobile 
                 stations from PDSN since system was last restarted."
        REFERENCE
                 "Refer to TIA/EIA international telecommunications
                  organization standard TR 45.4 for A10 session update
                  message and TR 45.6 for Accounting Model and CISCO PDSN 
                  release note."
        ::= { cCdmaTrafficStats 11 }

cCdmaReceivedPmipPkts OBJECT-TYPE
        SYNTAX      Counter32
        MAX-ACCESS  read-only
        STATUS      current
        DESCRIPTION
                "Total number of proxy mobile IP data packets received from 
                 mobile stations by PDSN since system was last restarted."
        REFERENCE
                 "Refer to TIA/EIA international telecommunications
                  organization standard TR 45.4 for A10 session update
                  message and TR 45.6 for Accounting Model and CISCO PDSN 
                  release note."
        ::= { cCdmaTrafficStats 12 }

cCdmaTransmittedSDBPkts OBJECT-TYPE
        SYNTAX      ZeroBasedCounter32
        MAX-ACCESS  read-only
        STATUS      current
        DESCRIPTION
                "Total number of SDB marked data packets sent to  
                 PCF from PDSN since system was last restarted."
        REFERENCE
                 "Refer to TIA/EIA international telecommunications
                  organization standard TR 45.4 for A10 session update
                  message and TR 45.6 for Accounting Model and CISCO
                  PDSN release note."
        ::= { cCdmaTrafficStats 13 }

cCdmaTransmittedSDBOctets OBJECT-TYPE
        SYNTAX      ZeroBasedCounter32
        MAX-ACCESS  read-only
        STATUS      current
        DESCRIPTION
                "Total number of SDB marked data data octets sent to
                 PCF from PDSN since system was last restarted."
        REFERENCE
                 "Refer to TIA/EIA international telecommunications
                  organization standard TR 45.4 for A10 session update
                  message and TR 45.6 for Accounting Model and CISCO
                  PDSN release note."
        ::= { cCdmaTrafficStats 14 }

cCdmaNoGREKeyPktDiscards OBJECT-TYPE
        SYNTAX      ZeroBasedCounter32
        MAX-ACCESS  read-only
        STATUS      current
        DESCRIPTION
                "Total number of packets discarded from PCF because 
                 GRE Key is missing since system was last restarted."
        REFERENCE
                 "Refer to TIA/EIA international telecommunications
                  organization standard TR 45.4 for A10 session update
                  message and TR 45.6 for Accounting Model and CISCO
                  PDSN release note."
        ::= { cCdmaTrafficStats 15 }

cCdmaNoSessionPktDiscards OBJECT-TYPE
        SYNTAX      ZeroBasedCounter32
        MAX-ACCESS  read-only
        STATUS      current
        DESCRIPTION
               "Total number of packets discarded from PCF because 
                session is not found since system was last restarted." 
        REFERENCE
                 "Refer to TIA/EIA international telecommunications
                  organization standard TR 45.4 for A10 session update
                  message and TR 45.6 for Accounting Model and CISCO
                  PDSN release note."
        ::= { cCdmaTrafficStats 16 }

cCdmaInvGREProtoPktDiscards OBJECT-TYPE
        SYNTAX      ZeroBasedCounter32
        MAX-ACCESS  read-only
        STATUS      current
        DESCRIPTION
               "Total number of packets discarded from PCF because GRE
                protocol is invalid since system was last restarted." 
        REFERENCE
                 "Refer to TIA/EIA international telecommunications
                  organization standard TR 45.4 for A10 session update
                  message and TR 45.6 for Accounting Model and CISCO
                  PDSN release note."
        ::= { cCdmaTrafficStats 17 }

cCdmaInvCheckSumPktDiscards OBJECT-TYPE
        SYNTAX      ZeroBasedCounter32
        MAX-ACCESS  read-only
        STATUS      current
        DESCRIPTION
               "Total number of packets discarded from PCF because 
                of invalid checksum since system was last restarted." 
        REFERENCE
                 "Refer to TIA/EIA international telecommunications
                  organization standard TR 45.4 for A10 session update
                  message and TR 45.6 for Accounting Model and CISCO
                  PDSN release note."
        ::= { cCdmaTrafficStats 18 }

-- ********************************************************************
-- Success flow counters: Simple IP, Mobile IP, Proxy Mobile IP, VPDN
-- ********************************************************************

cCdmaFlowSimpleIpSuccesses OBJECT-TYPE
        SYNTAX      Counter32
        MAX-ACCESS  read-only
        STATUS      current
        DESCRIPTION
                "Total number of Simple IP flow that has been established
                 successfully since system reboot."
        REFERENCE
                 "Refer to TIA/EIA international telecommunications
                  organization standard TR 45.4 for simple IP service."
        ::= { cCdmaFlowTypeStats 1 }

cCdmaFlowMobilIpSuccesses OBJECT-TYPE
        SYNTAX      Counter32
        MAX-ACCESS  read-only
        STATUS      current
        DESCRIPTION
                "Total number of mobile IP flow that has been established
                 successfully since system reboot."
        REFERENCE
                "Refer to TIA/EIA international telecommunications
                 organization standard TR 45.4 for mobile IP service."
        ::= { cCdmaFlowTypeStats 2 }

cCdmaFlowProxyIpSuccesses OBJECT-TYPE
        SYNTAX      Counter32
        MAX-ACCESS  read-only
        STATUS      current
        DESCRIPTION
                "Total number of proxy mobile IP flow that has been
                 established successfully since system reboot."
        REFERENCE
                 "Refer to TIA/EIA international telecommunications
                  organization standard TR 45.4 for A10 session update
                  message and TR 45.6 for Accounting Model and CISCO PDSN 
                  release note."
        ::= { cCdmaFlowTypeStats 3 }

cCdmaFlowVpdnSuccesses OBJECT-TYPE
        SYNTAX      Counter32
        MAX-ACCESS  read-only
        STATUS      current
        DESCRIPTION
                "Total number of VPDN flow that has been
                 established successfully since system reboot."
        REFERENCE
                 "Refer to TIA/EIA international telecommunications
                  organization standard TR 45.4 for A10 session update
                  message and TR 45.6 for Accounting Model and CISCO PDSN 
                  release note."
        ::= { cCdmaFlowTypeStats 4 }

cCdmaFlowSimpleIpFailures OBJECT-TYPE
        SYNTAX      Counter32
        MAX-ACCESS  read-only
        STATUS      current
        DESCRIPTION
                "Total number of simple IP flow setup request failed
                 since last system reboot."
        REFERENCE
                 "Refer to TIA/EIA international telecommunications
                  organization standard TR 45."
        ::= { cCdmaFlowTypeStats 5 }

cCdmaFlowMobileIpFailures OBJECT-TYPE
        SYNTAX      Counter32
        MAX-ACCESS  read-only
        STATUS      current
        DESCRIPTION
                "Total number of mobile IP flow setup request failed
                 since last system reboot."
        REFERENCE
                 "Refer to TIA/EIA international telecommunications
                  organization standard TR 45."
        ::= { cCdmaFlowTypeStats 6 }

cCdmaFlowProxyIpFailures OBJECT-TYPE
        SYNTAX      Counter32
        MAX-ACCESS  read-only
        STATUS      current
        DESCRIPTION
                "Total number of proxy mobile IP flow setup request 
                 failed since last system reboot."
        REFERENCE
                 "Refer to TIA/EIA international telecommunications
                  organization standard TR 45."
        ::= { cCdmaFlowTypeStats 7 }

cCdmaFlowVpdnFailures OBJECT-TYPE
        SYNTAX      Counter32
        MAX-ACCESS  read-only
        STATUS      current
        DESCRIPTION
                "Total number of VPDN flow setup request failed
                 since last system reboot."
        REFERENCE
                 "Refer to TIA/EIA international telecommunications
                  organization standard TR 45."
        ::= { cCdmaFlowTypeStats 8 }

cCdmaFlowUnknownTypeFailures  OBJECT-TYPE
        SYNTAX      Counter32
        MAX-ACCESS  read-only
        STATUS      current
        DESCRIPTION
                "Total number of unknown type flow setup request failed
                 since last system reboot."
        REFERENCE
                 "Refer to TIA/EIA international telecommunications
                  organization standard TR 45."
        ::= { cCdmaFlowTypeStats 9 }

-- *******************************************************************
-- Service option table:
-- *******************************************************************

cCdmaServiceTotalOptions OBJECT-TYPE
        SYNTAX      Counter32
        MAX-ACCESS  read-only
        STATUS      current
        DESCRIPTION
                "Total number of service options supported by this
                 PDSN."
        REFERENCE
                "Refer to 3GPP2 IOS 4.1 for description of defined
                 service options."
        ::= { cCdmaServiceOptionStats 1 }

cCdmaServiceOptionTable       OBJECT-TYPE
         SYNTAX      SEQUENCE OF CCdmaServiceOptionEntry
         MAX-ACCESS  not-accessible
         STATUS      current
         DESCRIPTION
                 "This is an independent table maintained by PDSN node. 
                  Each entry in this table is created when a new 
                  non-zero service option is processed during call
                  setup. An existing entry is not expected to be 
                  deleted unless system is restarted."
        ::= { cCdmaServiceOptionStats 2 }

cCdmaServiceOptionEntry OBJECT-TYPE
         SYNTAX      CCdmaServiceOptionEntry
         MAX-ACCESS  not-accessible
         STATUS      current
         DESCRIPTION
                 "A conceptual row in the cCdmaServiceOptionTable
                  table. Each row contains success and failures
                  statistics of a particular service option."
         INDEX { cCdmaServiceOptionIndex }
         ::= { cCdmaServiceOptionTable 1 }

CCdmaServiceOptionEntry ::=
         SEQUENCE {
             cCdmaServiceOptionIndex             INTEGER,
             cCdmaServiceOptionSucesses          Counter32,
             cCdmaServiceOptionFailures          Counter32
         }

cCdmaServiceOptionIndex OBJECT-TYPE
         SYNTAX      INTEGER { 
                         smsRate1(6),
                         loopback13K(9),
                         asyncDataRate2(12),
                         group3FaxRate2(13),
                         smsRate2(14),
                         packetData144k(15),
                         otapaRate1(18),
                         otapaRate2(19),
                         packetDataRs1fRs1r(22),
                         packetDataRs1fRs2r(23),
                         packetDataRs2fRs1r(24),
                         packetDataRs2fRs2(25),
                         is2000TestData(32),
                         packetData3G(33),
                         isdn64k(37),
                         is2000Markov(54),
                         is2000Loopback(55),
                         packetDataRev1(4103)
                     }
         MAX-ACCESS  not-accessible
         STATUS      current
         DESCRIPTION
                 "This object reflects a service option as defined by 
                  IOS 4.1. It is used to uniquely index entries in this 
                  table. The following options are defined in 3GPP2 4.1:

                  - smsRate1(6): SMS rate set 1

                  - loopback13K(9): 13K loopback

                  - asyncDataRate2(12) Asynchronous data rate set 2

                  - group3FaxRate2(13) Group 3 fax rate set 2

                  - smsRate2(14) SMS rate set 2

                  - packetData144k(15) Packet data service: Internet
                     or ISO protocol stack (14.4kbps)
                  - otapaRate1(18): OTAPA rate set 1

                  - otapaRate2(19): OTAPA rate set 2

                  - is2000TestData(32): IS-2000 test data

                  - is2000Markov(54): IS-2000 Markov

                  - is2000Loopback(55): IS-2000 loopback

                  - packetDataRs1fRs1r(22): High speed packet data 
                    service: internet or ISO protocol stack (RS1 
                    forward, RS1 reverse)

                  - packetDataRs1fRs2r(23): High speed packet data 
                    service: internet or ISO protocol stack (RS1
                    forward, RS2 reverse)

                  - packetDataRs2fRs1r(24): High speed packet data 
                    service: internet or ISO protocol stack (RS2
                    forward, RS1 reverse)

                  - packetDataRs2fRs2(25): High speed packet data 
                    service: internet or ISO protocol stack (RS2 
                    forward, RS2 reverse)

                  - packetData3G(33): 3G high speed packet data

                  - isdn64k(37),: ISDN interworking service (64kbps)

                  - packetDataRev1(4103): Packet data service: 
                    Internet or ISO protocol stack, revision 1
                    (9.6 or 14.4kbps)"
         REFERENCE
                 "Refer to 3GPP2 IOS 4.1 for details."
         ::= { cCdmaServiceOptionEntry 1 }

cCdmaServiceOptionSucesses OBJECT-TYPE
         SYNTAX      Counter32
         MAX-ACCESS  read-only
         STATUS      current
         DESCRIPTION
                 "Total number of RP session setup success for a 
                  particular service option as defined by IOS 4.1."
         ::= { cCdmaServiceOptionEntry 2 }

cCdmaServiceOptionFailures OBJECT-TYPE
         SYNTAX      Counter32
         MAX-ACCESS  read-only
         STATUS      current
         DESCRIPTION
                 "Total number of RP session setup failure for a 
                  particular service option as defined by IOS 4.1."
         ::= { cCdmaServiceOptionEntry 3 }

-- ******************************************************************
-- Handoff statistics
-- ******************************************************************
cCdmaInterPcfHandoffs OBJECT-TYPE
         SYNTAX      Counter32
         MAX-ACCESS  read-only
         STATUS      current
         DESCRIPTION
                 "Total number of inter PCF handoffs since system last
                  restart."
         REFERENCE
                 "Refer to 3GPP2 IOS 4.1 for details."
         ::= { cCdmaHandoffStats 1 }

cCdmaInterPdsnHandoffs OBJECT-TYPE
         SYNTAX      Counter32
         MAX-ACCESS  read-only
         STATUS      current
         DESCRIPTION
                 "Total number of inter PDSN handoffs since system last
                  restart."
         REFERENCE
                 "Refer to 3GPP2 IOS 4.1 for details."
         ::= { cCdmaHandoffStats 2 }

cCdmaIdChangeHandoffs OBJECT-TYPE
         SYNTAX      Counter32
         MAX-ACCESS  read-only
         STATUS      current
         DESCRIPTION
                 "Total number of handoffs due to CANID/PANID change 
                  since system last restart."
         REFERENCE
                 "Refer to 3GPP2 IOS 4.1 for details."
         ::= { cCdmaHandoffStats 3 }

-- *******************************************************************
-- Status change statistics:
-- *******************************************************************
cCdmaStatusIS2OOSes OBJECT-TYPE
         SYNTAX      Counter32
         MAX-ACCESS  read-only
         STATUS      current
         DESCRIPTION
                 "Total number of status changes from IS to OOS."
         ::= { cCdmaStatusChangeStats 1 }

cCdmaStatusOOS2ISes OBJECT-TYPE
         SYNTAX      Counter32
         MAX-ACCESS  read-only
         STATUS      current
         DESCRIPTION
                 "Total number of status changes from OOS to IS."
         ::= { cCdmaStatusChangeStats 2 }

-- ******************************************************************
-- Addressing schema statistics:
-- ******************************************************************
cCdmaAddressStaticSIPs OBJECT-TYPE
         SYNTAX      Counter32
         MAX-ACCESS  read-only
         STATUS      current
         DESCRIPTION
                 "Total number of simple IP calls which negotiated
                  static IP addresses."
         ::= { cCdmaAddressSchemeStats 1 }

cCdmaAddressDynamicSIPs OBJECT-TYPE
         SYNTAX      Counter32
         MAX-ACCESS  read-only
         STATUS      current
         DESCRIPTION
                 "Total number of simple IP calls which negotiated
                  dynamic IP addresses."
         ::= { cCdmaAddressSchemeStats 2 }

cCdmaAddressStaticMIPs OBJECT-TYPE
         SYNTAX      Counter32
         MAX-ACCESS  read-only
         STATUS      current
         DESCRIPTION
                 "Total number of mobile IP calls which negotiated
                  static IP addresses."
         ::= { cCdmaAddressSchemeStats 3 }

cCdmaAddressDynamicMIPs OBJECT-TYPE
         SYNTAX      Counter32
         MAX-ACCESS  read-only
         STATUS      current
         DESCRIPTION
                 "Total number of mobile IP calls which negotiated
                  dynamic IP addresses."
         ::= { cCdmaAddressSchemeStats 4 }

cCdmaAddressStaticPMIPs OBJECT-TYPE
         SYNTAX      Counter32
         MAX-ACCESS  read-only
         STATUS      current
         DESCRIPTION
                 "Total number of proxy mobile IP calls which 
                  negotiated static IP addresses."
         ::= { cCdmaAddressSchemeStats 5 }

cCdmaAddressDynamicPMIPs OBJECT-TYPE
         SYNTAX      Counter32
         MAX-ACCESS  read-only
         STATUS      current
         DESCRIPTION
                 "Total number of proxy mobile IP calls which 
                  negotiated dynamic IP addresses."
         ::= { cCdmaAddressSchemeStats 6 }

cCdmaAddressStaticVPDNs  OBJECT-TYPE
         SYNTAX      Counter32
         MAX-ACCESS  read-only
         STATUS      current
         DESCRIPTION
                 "Total number of VPDN calls which negotiated
                  static IP addresses."
         ::= { cCdmaAddressSchemeStats 7 }

cCdmaAddressDynamicVPDNs  OBJECT-TYPE
         SYNTAX      Counter32
         MAX-ACCESS  read-only
         STATUS      current
         DESCRIPTION
                 "Total number of VPDN calls which negotiated
                  dynamic IP addresses."
         ::= { cCdmaAddressSchemeStats 8 }
         
-- ******************************************************************
-- * CDMA PDSN PCF and Service Option based RP Registration Statistics 
-- ******************************************************************

cCdmaPcfSoRpRegStatsTable       OBJECT-TYPE
         SYNTAX      SEQUENCE OF CCdmaPcfSoRpRegStatsEntry
         MAX-ACCESS  not-accessible
         STATUS      current
         DESCRIPTION
                 "A table containing RP registration statistics, such
                  as number of registration requests, registration 
                  Replies etc., grouped and indexed on the basis of
                  PCF's IP address and the service option." 
         ::= { cCdmaPcfSoRpRegStats 1 }

cCdmaPcfSoRpRegStatsEntry   OBJECT-TYPE
         SYNTAX      CCdmaPcfSoRpRegStatsEntry
         MAX-ACCESS  not-accessible
         STATUS      current
         DESCRIPTION
                 "The RP registration statistics pertaining to a unique
                  combination of PCF and service option."
         INDEX { cCdmaPcfSoRpRegIpAddrType,                 
                 cCdmaPcfSoRpRegIpAddr,
                 cCdmaPcfSoRpRegServiceOption }
         ::= { cCdmaPcfSoRpRegStatsTable 1 }
 
CCdmaPcfSoRpRegStatsEntry ::=
         SEQUENCE {
             cCdmaPcfSoRpRegIpAddrType            InetAddressType,
             cCdmaPcfSoRpRegIpAddr                InetAddress,
             cCdmaPcfSoRpRegServiceOption         CCdmaServiceOption,
             cCdmaPcfSoRpRegRcvdReqs              ZeroBasedCounter32,
             cCdmaPcfSoRpRegAcptdReqs             ZeroBasedCounter32,
             cCdmaPcfSoRpRegDeniedReqs            ZeroBasedCounter32,
             cCdmaPcfSoRpRegDiscardedReqs         ZeroBasedCounter32,
             cCdmaPcfSoRpInitRegAcptdReqs         ZeroBasedCounter32,
             cCdmaPcfSoRpInitRegDeniedReqs        ZeroBasedCounter32,
             cCdmaPcfSoRpReRegAcptdReqs           ZeroBasedCounter32,
             cCdmaPcfSoRpReRegDeniedReqs          ZeroBasedCounter32,
             cCdmaPcfSoRpDeRegAcptdReqs           ZeroBasedCounter32,
             cCdmaPcfSoRpDeRegDeniedReqs          ZeroBasedCounter32,
             cCdmaPcfSoRpRegPcfUnknwnFails        ZeroBasedCounter32,
             cCdmaPcfSoRpRegAdmnFails             ZeroBasedCounter32,
             cCdmaPcfSoRpRegNoRsrcFails           ZeroBasedCounter32,
             cCdmaPcfSoRpRegMNAuthFails           ZeroBasedCounter32,
             cCdmaPcfSoRpRegIdMismatFails         ZeroBasedCounter32,
             cCdmaPcfSoRpRegBadReqFails           ZeroBasedCounter32,
             cCdmaPcfSoRpRegUnkPdsnFails          ZeroBasedCounter32,
             cCdmaPcfSoRpRegNoRevTunFails         ZeroBasedCounter32,
             cCdmaPcfSoRpRegTBitNSetFails         ZeroBasedCounter32,
             cCdmaPcfSoRpRegBadCVSEFails          ZeroBasedCounter32,
             cCdmaPcfSoRpInitRegRcvdReqs          ZeroBasedCounter32,
             cCdmaPcfSoRpInitRegDiscardedReqs     ZeroBasedCounter32,
             cCdmaPcfSoRpReRegRcvdReqs            ZeroBasedCounter32,
             cCdmaPcfSoRpReRegDiscardedReqs       ZeroBasedCounter32,
             cCdmaPcfSoRpDeRegRcvdReqs            ZeroBasedCounter32,
             cCdmaPcfSoRpDeRegDiscardedReqs       ZeroBasedCounter32,
             cCdmaPcfSoRpHandoffRegRcvdReqs       ZeroBasedCounter32,
             cCdmaPcfSoRpHandoffRegAcptdReqs      ZeroBasedCounter32,        
             cCdmaPcfSoRpHandoffRegDeniedReqs     ZeroBasedCounter32,
             cCdmaPcfSoRpHandoffRegDiscardedReqs  ZeroBasedCounter32,        
             cCdmaPcfSoRpReRegAirlinkStarts       ZeroBasedCounter32,
             cCdmaPcfSoRpReRegAirlinkStops        ZeroBasedCounter32,
             cCdmaPcfSoRpDeRegAirlinkStops        ZeroBasedCounter32
         }
cCdmaPcfSoRpRegIpAddrType   OBJECT-TYPE
         SYNTAX      InetAddressType
         MAX-ACCESS  not-accessible
         STATUS      current
         DESCRIPTION
                 "Represents the type of the address specified by
                 cCdmaPcfSoRpRegIpAddr."
         ::= { cCdmaPcfSoRpRegStatsEntry 1 }

cCdmaPcfSoRpRegIpAddr   OBJECT-TYPE
         SYNTAX      InetAddress
         MAX-ACCESS  not-accessible
         STATUS      current
         DESCRIPTION
                 "The IP address of the PCF that serves the 
                  mobile node."
         ::= { cCdmaPcfSoRpRegStatsEntry 2 }
         
cCdmaPcfSoRpRegServiceOption OBJECT-TYPE
         SYNTAX      CCdmaServiceOption
         MAX-ACCESS  not-accessible
         STATUS      current
         DESCRIPTION
                 "The service option received as part of the 
                  registration request."
         ::= { cCdmaPcfSoRpRegStatsEntry 3 }        

cCdmaPcfSoRpRegRcvdReqs OBJECT-TYPE
        SYNTAX      ZeroBasedCounter32
        MAX-ACCESS  read-only
        STATUS      current
        DESCRIPTION
                "Total number of A11 registration requests received
                 since the system was last restarted."
        REFERENCE
                 "Refer to TIA/EIA international telecommunications
                  organization standard TR 45.4 for details about
                  A10/A11(R-P) interface."
        ::= { cCdmaPcfSoRpRegStatsEntry 4 }

cCdmaPcfSoRpRegAcptdReqs OBJECT-TYPE
        SYNTAX      ZeroBasedCounter32
        MAX-ACCESS  read-only
        STATUS      current
        DESCRIPTION
                "Total number of A11 registration requests accepted
                 since the system was last restarted.  The code field
                 in the corresponding registration reply message, is
                 set to zero."
        REFERENCE
                 "Refer to TIA/EIA international telecommunications
                  organization standard TR 45.4 for details about
                  A10/A11(R-P) interface."
        ::= { cCdmaPcfSoRpRegStatsEntry 5 }

cCdmaPcfSoRpRegDeniedReqs OBJECT-TYPE
        SYNTAX      ZeroBasedCounter32
        MAX-ACCESS  read-only
        STATUS      current
        DESCRIPTION
                "Total number of A11 registration requests denied
                 since the system was last restarted.  The code field
                 in the corresponding registration reply message is
                 set to non-zero."
        REFERENCE
                 "Refer to TIA/EIA international telecommunications
                  organization standard TR 45.4 for details about
                  A10/A11(R-P) interface."
        ::= { cCdmaPcfSoRpRegStatsEntry 6 }

cCdmaPcfSoRpRegDiscardedReqs OBJECT-TYPE
        SYNTAX      ZeroBasedCounter32
        MAX-ACCESS  read-only
        STATUS      current
        DESCRIPTION
                "Total number of A11 registration requests silently
                 discarded  since the system was last restarted.  A
                 corresponding registration reply message is not
                 returned for these A11 registration requests."
        REFERENCE
                 "Refer to TIA/EIA international telecommunications
                  organization standard TR 45.4 for details about
                  A10/A11(R-P) interface."
        ::= { cCdmaPcfSoRpRegStatsEntry 7 }

cCdmaPcfSoRpInitRegAcptdReqs OBJECT-TYPE
        SYNTAX      ZeroBasedCounter32
        MAX-ACCESS  read-only
        STATUS      current
        DESCRIPTION
                "Total number of accepted A11 registration requests
                 meant for establishing new R-P connections, since
                 the system was last restarted.  These A11 registration
                 requests contain the connection setup airlink record.
                 The code field in the corresponding registration reply
                 message is set to zero."
        REFERENCE
                 "Refer to TIA/EIA international telecommunications
                  organization standard TR 45.4 for details about
                  A10/A11(R-P) interface."
        ::= { cCdmaPcfSoRpRegStatsEntry 8 }

cCdmaPcfSoRpInitRegDeniedReqs OBJECT-TYPE
        SYNTAX      ZeroBasedCounter32
        MAX-ACCESS  read-only
        STATUS      current
        DESCRIPTION
                "Total number of denied A11 registration requests
                 meant for establishing new R-P connections, since
                 the system was last restarted.  These A11 registration
                 requests contain the connection setup airlink record.
                 The code field in the corresponding registration reply
                 message set to non-zero."

        REFERENCE
                 "Refer to TIA/EIA international telecommunications
                  organization standard TR 45.4 for details about
                  A10/A11(R-P) interface."
        ::= { cCdmaPcfSoRpRegStatsEntry 9 }

cCdmaPcfSoRpReRegAcptdReqs OBJECT-TYPE
        SYNTAX      ZeroBasedCounter32
        MAX-ACCESS  read-only
        STATUS      current
        DESCRIPTION
                "Total number of accepted A11 registration requests
                 meant for refreshing the already established R-P
                 connections, since the system was last restarted.  The
                 Code field in the corresponding registration reply
                 message is set to zero."
        REFERENCE
                 "Refer to TIA/EIA international telecommunications
                  organization standard TR 45.4 for details about
                  A10/A11(R-P) interface."
        ::= { cCdmaPcfSoRpRegStatsEntry 10 }

cCdmaPcfSoRpReRegDeniedReqs OBJECT-TYPE
        SYNTAX      ZeroBasedCounter32
        MAX-ACCESS  read-only
        STATUS      current
        DESCRIPTION
                "Total number of denied A11 registration requests
                 meant for refreshing the already established R-P
                 connections, since the system was last restarted.  The
                 Code field in the corresponding registration reply
                 message is set to non-zero."
        REFERENCE
                 "Refer to TIA/EIA international telecommunications
                  organization standard TR 45.4 for details about
                  A10/A11(R-P) interface."
        ::= { cCdmaPcfSoRpRegStatsEntry 11 }

cCdmaPcfSoRpDeRegAcptdReqs OBJECT-TYPE
        SYNTAX      ZeroBasedCounter32
        MAX-ACCESS  read-only
        STATUS      current
        DESCRIPTION
                "Total number of accepted A11 registration requests
                 meant for de-establishing the already established R-P
                 connections, since the system was last restarted.  The
                 Code field in the corresponding registration reply
                 message is set to zero."
        REFERENCE
                 "Refer to TIA/EIA international telecommunications
                  organization standard TR 45.4 for details about
                  A10/A11(R-P) interface."
        ::= { cCdmaPcfSoRpRegStatsEntry 12 }

cCdmaPcfSoRpDeRegDeniedReqs OBJECT-TYPE
        SYNTAX      ZeroBasedCounter32
        MAX-ACCESS  read-only
        STATUS      current
        DESCRIPTION
                "Total number of denied A11 registration requests
                 meant for de-establishing the already established R-P
                 connections, since the system was last restarted.  The
                 Code field in the corresponding registration reply
                 message is set to non-zero."
        REFERENCE
                 "Refer to TIA/EIA international telecommunications
                  organization standard TR 45.4 for details about
                  A10/A11(R-P) interface."
        ::= { cCdmaPcfSoRpRegStatsEntry 13 }

cCdmaPcfSoRpRegPcfUnknwnFails OBJECT-TYPE
        SYNTAX      ZeroBasedCounter32
        MAX-ACCESS  read-only
        STATUS      current
        DESCRIPTION
                "The number of registration requests failed because PCF
                 address is not in PDSN's list of configured PCFs for
                 unspecified reason since system was last restarted."
        REFERENCE
                 "Refer to TIA/EIA international telecommunications
                  organization standard TR 45.4 for details about A10
                  session setup errors."
        ::= { cCdmaPcfSoRpRegStatsEntry 14 }

cCdmaPcfSoRpRegAdmnFails OBJECT-TYPE
        SYNTAX      ZeroBasedCounter32
        MAX-ACCESS  read-only
        STATUS      current
        DESCRIPTION
                "The number of registration requests failed because PCF
                 address is not in PDSN's list of configured PCFs since
                 system was last restarted."
        REFERENCE
                 "Refer to TIA/EIA international telecommunications
                  organization standard TR 45.4 for details about A10
                  session setup errors."
        ::= { cCdmaPcfSoRpRegStatsEntry 15 }

cCdmaPcfSoRpRegNoRsrcFails OBJECT-TYPE
        SYNTAX      ZeroBasedCounter32
        MAX-ACCESS  read-only
        STATUS      current
        DESCRIPTION
                "The number of registration requests failed because
                 max number of PCFs or max number of sessions reached
                 or out of system resources since system was last
                 restarted."
        REFERENCE
                 "Refer to TIA/EIA international telecommunications
                  organization standard TR 45.4 for details about A10
                  session setup errors."
        ::= { cCdmaPcfSoRpRegStatsEntry 16 }

cCdmaPcfSoRpRegMNAuthFails OBJECT-TYPE
        SYNTAX      ZeroBasedCounter32
        MAX-ACCESS  read-only
        STATUS      current
        DESCRIPTION
                "The number of registration requests failed due to
                 MN authentication failure since system was last
                 restarted."
        REFERENCE
                 "Refer to TIA/EIA international telecommunications
                  organization standard TR 45.4 for details about A10
                  session setup errors."
        ::= { cCdmaPcfSoRpRegStatsEntry 17 }

cCdmaPcfSoRpRegIdMismatFails OBJECT-TYPE
        SYNTAX      ZeroBasedCounter32
        MAX-ACCESS  read-only
        STATUS      current
        DESCRIPTION
                "The number of registration requests failed because
                 of identification mismatch since system was last
                 restarted."
        REFERENCE
                 "Refer to TIA/EIA international telecommunications
                  organization standard TR 45.4 for details about A10
                  session setup errors."
        ::= { cCdmaPcfSoRpRegStatsEntry 18 }

cCdmaPcfSoRpRegBadReqFails OBJECT-TYPE
        SYNTAX      ZeroBasedCounter32
        MAX-ACCESS  read-only
        STATUS      current
        DESCRIPTION
                "The number of registration requests failed
                 because of badly formed request since system was last
                 restarted."
        REFERENCE
                 "Refer to TIA/EIA international telecommunications
                  organization standard TR 45.4 for details about A10
                  session setup errors."
        ::= { cCdmaPcfSoRpRegStatsEntry 19 }

cCdmaPcfSoRpRegUnkPdsnFails OBJECT-TYPE
        SYNTAX      ZeroBasedCounter32
        MAX-ACCESS  read-only
        STATUS      current
        DESCRIPTION
                "The number of registration requests failed
                 because of unknown PDSN/HA Address since system was
                 last restarted."
        REFERENCE
                 "Refer to TIA/EIA international telecommunications
                  organization standard TR 45.4 for details about A10
                  session setup errors."
        ::= { cCdmaPcfSoRpRegStatsEntry 20 }

cCdmaPcfSoRpRegNoRevTunFails OBJECT-TYPE
        SYNTAX      ZeroBasedCounter32
        MAX-ACCESS  read-only
        STATUS      current
        DESCRIPTION
                "The number of registration requests failed because
                 FA to HA reverse tunnel setup failed since system was
                 last restarted."
        REFERENCE
                 "RFC-2344."
        ::= { cCdmaPcfSoRpRegStatsEntry 21 }

cCdmaPcfSoRpRegTBitNSetFails OBJECT-TYPE
        SYNTAX      ZeroBasedCounter32
        MAX-ACCESS  read-only
        STATUS      current
        DESCRIPTION
                "The number of registration requests failed because
                 reverse tunnel is required, but T bit is not set since
                 system was last restarted."
        REFERENCE
                 "Refer to TIA/EIA international telecommunications
                  organization standard TR 45.4 for details about A10
                  session setup errors."
        ::= { cCdmaPcfSoRpRegStatsEntry 22 }

cCdmaPcfSoRpRegBadCVSEFails OBJECT-TYPE
        SYNTAX      ZeroBasedCounter32
        MAX-ACCESS  read-only
        STATUS      current
        DESCRIPTION
                "The number of registration requests failed because of
                 unsupported vendor codes in CVSE since system was last
                 restarted."
        REFERENCE
                 "Refer to TIA/EIA international telecommunications
                  organization standard TR 45.4 for details about A10
                  session setup errors."
        ::= { cCdmaPcfSoRpRegStatsEntry 23 }

cCdmaPcfSoRpInitRegRcvdReqs OBJECT-TYPE
        SYNTAX      ZeroBasedCounter32
        MAX-ACCESS  read-only
        STATUS      current
        DESCRIPTION
                "The number of Initial A11 Registration requests 
                 received since system was last restarted."
        REFERENCE
                 "Refer to TIA/EIA international telecommunications 
                  organization standard TR 45.4 for details about A10 
                  session setup errors."
        ::= { cCdmaPcfSoRpRegStatsEntry 24 }

cCdmaPcfSoRpInitRegDiscardedReqs OBJECT-TYPE
        SYNTAX      ZeroBasedCounter32
        MAX-ACCESS  read-only
        STATUS      current
        DESCRIPTION
                "The number of Initial A11 Registration requests 
                 silently discarded since system was last restarted."
        REFERENCE
                 "Refer to TIA/EIA international telecommunications 
                  organization standard TR 45.4 for details about A10 
                  session setup errors."
        ::= { cCdmaPcfSoRpRegStatsEntry 25 }

cCdmaPcfSoRpReRegRcvdReqs OBJECT-TYPE
        SYNTAX      ZeroBasedCounter32
        MAX-ACCESS  read-only
        STATUS      current
        DESCRIPTION
                "The number of A11 Re-Registration requests 
                 received since system was last restarted."
        REFERENCE
                 "Refer to TIA/EIA international telecommunications 
                  organization standard TR 45.4 for details about A10 
                  session setup errors."
        ::= { cCdmaPcfSoRpRegStatsEntry 26 }

cCdmaPcfSoRpReRegDiscardedReqs OBJECT-TYPE
        SYNTAX      ZeroBasedCounter32
        MAX-ACCESS  read-only
        STATUS      current
        DESCRIPTION
                "The number of A11 Re-Registration requests 
                 silently discarded since system was last restarted."
        REFERENCE
                 "Refer to TIA/EIA international telecommunications 
                  organization standard TR 45.4 for details about A10 
                  session setup errors."
        ::= { cCdmaPcfSoRpRegStatsEntry 27 }

cCdmaPcfSoRpDeRegRcvdReqs OBJECT-TYPE
        SYNTAX      ZeroBasedCounter32
        MAX-ACCESS  read-only
        STATUS      current
        DESCRIPTION
                "The number of A11 De-Registration requests 
                 received since system was last restarted."
        REFERENCE
                 "Refer to TIA/EIA international telecommunications 
                  organization standard TR 45.4 for details about A10 
                  session setup errors."
        ::= { cCdmaPcfSoRpRegStatsEntry 28 }

cCdmaPcfSoRpDeRegDiscardedReqs OBJECT-TYPE
        SYNTAX      ZeroBasedCounter32
        MAX-ACCESS  read-only
        STATUS      current
        DESCRIPTION
                "The number of A11 De-Registration requests 
                 silently discarded since system was last restarted."
        REFERENCE
                 "Refer to TIA/EIA international telecommunications 
                  organization standard TR 45.4 for details about A10 
                  session setup errors."
        ::= { cCdmaPcfSoRpRegStatsEntry 29 }

cCdmaPcfSoRpHandoffRegRcvdReqs OBJECT-TYPE
        SYNTAX      ZeroBasedCounter32
        MAX-ACCESS  read-only
        STATUS      current
        DESCRIPTION
                "The number of A11 Handoff Registration requests 
                 received since system was last restarted."
        REFERENCE
                 "Refer to TIA/EIA international telecommunications 
                  organization standard TR 45.4 for details about A10 
                  session setup errors."
        ::= { cCdmaPcfSoRpRegStatsEntry 30 }

cCdmaPcfSoRpHandoffRegAcptdReqs OBJECT-TYPE
        SYNTAX      ZeroBasedCounter32
        MAX-ACCESS  read-only
        STATUS      current
        DESCRIPTION
                "Total number of accepted handoff A11 Registration
                 Requests meant for already existing session,
                 since the system was last restarted."
        REFERENCE
                 "Refer to TIA/EIA international telecommunications
                  organization standard TR 45.4 for details about
                  A10/A11(R-P) interface."
        ::= { cCdmaPcfSoRpRegStatsEntry 31 }

cCdmaPcfSoRpHandoffRegDeniedReqs OBJECT-TYPE
        SYNTAX      ZeroBasedCounter32
        MAX-ACCESS  read-only
        STATUS      current
        DESCRIPTION
                "Total number of denied handoff A11 Registration
                 Requests meant for already existing session, 
                 since the system was last restarted."

        REFERENCE
                 "Refer to TIA/EIA international telecommunications
                  organization standard TR 45.4 for details about
                  A10/A11(R-P) interface."
        ::= { cCdmaPcfSoRpRegStatsEntry 32 }

cCdmaPcfSoRpHandoffRegDiscardedReqs OBJECT-TYPE
        SYNTAX      ZeroBasedCounter32
        MAX-ACCESS  read-only
        STATUS      current
        DESCRIPTION
                "The number of handoff A11 Registration requests 
                 silently discarded since system was last restarted."
        REFERENCE
                 "Refer to TIA/EIA international telecommunications 
                  organization standard TR 45.4 for details about A10 
                  session setup errors."
        ::= { cCdmaPcfSoRpRegStatsEntry 33 }

cCdmaPcfSoRpReRegAirlinkStarts OBJECT-TYPE
        SYNTAX      ZeroBasedCounter32
        MAX-ACCESS  read-only
        STATUS      current
        DESCRIPTION
                "The number of A11 Re-Registration requests 
                 containing Airlink Start since system was last restarted."
        REFERENCE
                 "Refer to TIA/EIA international telecommunications 
                  organization standard TR 45.4 for details about A10 
                  session setup errors."
        ::= { cCdmaPcfSoRpRegStatsEntry 34 }

cCdmaPcfSoRpReRegAirlinkStops OBJECT-TYPE
        SYNTAX      ZeroBasedCounter32
        MAX-ACCESS  read-only
        STATUS      current
        DESCRIPTION
                "The number of A11 Re-Registration requests 
                 containing Airlink Stop since system was last restarted."
        REFERENCE
                 "Refer to TIA/EIA international telecommunications 
                  organization standard TR 45.4 for details about A10 
                  session setup errors."
        ::= { cCdmaPcfSoRpRegStatsEntry 35 }

cCdmaPcfSoRpDeRegAirlinkStops OBJECT-TYPE
        SYNTAX      ZeroBasedCounter32
        MAX-ACCESS  read-only
        STATUS      current
        DESCRIPTION
                "The number of A11 De-Registration requests 
                 containing Airlink Stop since system was last restarted."
        REFERENCE
                 "Refer to TIA/EIA international telecommunications 
                  organization standard TR 45.4 for details about A10 
                  session setup errors."
        ::= { cCdmaPcfSoRpRegStatsEntry 36 }

-- ******************************************************************
-- * CDMA PDSN PCF and Service Option based RP Reg Update Statistics 
-- ******************************************************************

cCdmaPcfSoRpUpdStatsTable       OBJECT-TYPE
         SYNTAX      SEQUENCE OF CCdmaPcfSoRpUpdStatsEntry
         MAX-ACCESS  not-accessible
         STATUS      current
         DESCRIPTION
                 "A table containing RP update statistics such as
                  RP updates sent, acks received etc., grouped and
                  index on the basis of PCF's IP address and the
                  service option."
         ::= { cCdmaPcfSoRpUpdStats 1 }

cCdmaPcfSoRpUpdStatsEntry   OBJECT-TYPE
         SYNTAX      CCdmaPcfSoRpUpdStatsEntry
         MAX-ACCESS  not-accessible
         STATUS      current
         DESCRIPTION
                 "The RP update statistics pertaining to a unique
                  combination of PCF and service option."
         INDEX { cCdmaPcfSoRpUpdIpAddrType,
                 cCdmaPcfSoRpUpdIpAddr, 
                 cCdmaPcfSoRpUpdServiceOption }
         ::= { cCdmaPcfSoRpUpdStatsTable 1 }

CCdmaPcfSoRpUpdStatsEntry ::=
         SEQUENCE {
             cCdmaPcfSoRpUpdIpAddrType            InetAddressType,
             cCdmaPcfSoRpUpdIpAddr                InetAddress,
             cCdmaPcfSoRpUpdServiceOption         CCdmaServiceOption,
             cCdmaPcfSoRpUpdTxdReqs               ZeroBasedCounter32,
             cCdmaPcfSoRpUpdAcptdReqs             ZeroBasedCounter32,
             cCdmaPcfSoRpUpdDeniedReqs            ZeroBasedCounter32,
             cCdmaPcfSoRpUpdNotAckedReqs          ZeroBasedCounter32,
             cCdmaPcfSoRpUpdInitTxdReqs           ZeroBasedCounter32,
             cCdmaPcfSoRpUpdReTxdReqs             ZeroBasedCounter32,
             cCdmaPcfSoRpUpdRcvdAcks              ZeroBasedCounter32,
             cCdmaPcfSoRpUpdDiscardedAcks         ZeroBasedCounter32,
             cCdmaPcfSoRpUpdRpLifeExpReqs         ZeroBasedCounter32,
             cCdmaPcfSoRpUpdPPPtermReqs           ZeroBasedCounter32,
             cCdmaPcfSoRpUpdOtherReaReqs          ZeroBasedCounter32,
             cCdmaPcfSoRpUpdReaUnSpecFails        ZeroBasedCounter32,
             cCdmaPcfSoRpUpdAdmnFails             ZeroBasedCounter32,
             cCdmaPcfSoRpUpdMNAuthFails           ZeroBasedCounter32,
             cCdmaPcfSoRpUpdIdMismatFails         ZeroBasedCounter32,
             cCdmaPcfSoRpUpdBadReqFails           ZeroBasedCounter32,
             cCdmaSoRpUpdPcfHandoffs              ZeroBasedCounter32,
             cCdmaSoRpUpdHandoffNotAckedReqs      ZeroBasedCounter32,
             cCdmaSoRpUpdHandoffReceivedAcks      ZeroBasedCounter32,
             cCdmaSoRpUpdHandoffAcceptedReqs      ZeroBasedCounter32,
             cCdmaSoRpUpdHandoffDeniedReqs        ZeroBasedCounter32,
             cCdmaSoRpUpdHandoffDiscardedAcks     ZeroBasedCounter32,
             cCdmaSoRpUpdHandoffInitTxdReqs       ZeroBasedCounter32,
             cCdmaSoRpUpdHandoffReTxdReqs         ZeroBasedCounter32,
             cCdmaSoRpUpdHandoffReaUnSpecFails    ZeroBasedCounter32,
             cCdmaSoRpUpdHandoffAdmProhibFails    ZeroBasedCounter32,
             cCdmaSoRpUpdHandoffMNAuthenFails     ZeroBasedCounter32,
             cCdmaSoRpUpdHandoffIdMismatchFails   ZeroBasedCounter32,
             cCdmaSoRpUpdHandoffBadReqFails       ZeroBasedCounter32
         }             

cCdmaPcfSoRpUpdIpAddrType   OBJECT-TYPE
         SYNTAX      InetAddressType
         MAX-ACCESS  not-accessible
         STATUS      current
         DESCRIPTION
                 "Represents the type of the address specified by
                  cCdmaPcfSoRpUpdIpAddr."
         ::= { cCdmaPcfSoRpUpdStatsEntry 1 }

cCdmaPcfSoRpUpdIpAddr   OBJECT-TYPE
         SYNTAX      InetAddress
         MAX-ACCESS  not-accessible
         STATUS      current
         DESCRIPTION
                 "The IP address of the PCF that serves
                  the mobile node."
         ::= { cCdmaPcfSoRpUpdStatsEntry 2 }
         
cCdmaPcfSoRpUpdServiceOption OBJECT-TYPE
         SYNTAX      CCdmaServiceOption
         MAX-ACCESS  not-accessible
         STATUS      current
         DESCRIPTION
                 "A packet data service option, specifies a means
                  between MS and RN to establish and maintain cdma2000
                  traffic channels for packet data service."
         ::= { cCdmaPcfSoRpUpdStatsEntry 3 }

cCdmaPcfSoRpUpdTxdReqs OBJECT-TYPE
        SYNTAX      ZeroBasedCounter32
        MAX-ACCESS  read-only
        STATUS      current
        DESCRIPTION
                "Total number of A11 registration updates transmitted
                 since system was last restarted."
        REFERENCE
                 "Refer to TIA/EIA international telecommunications
                  organization standard TR 45.4 for A10 session update
                  message and TR 45.6 for Accounting Model."
        ::= { cCdmaPcfSoRpUpdStatsEntry 4 }

cCdmaPcfSoRpUpdAcptdReqs OBJECT-TYPE
        SYNTAX      ZeroBasedCounter32
        MAX-ACCESS  read-only
        STATUS      current
        DESCRIPTION
                "Total number of A11 registration acknowledgements
                 received with the Status field set to zero (indicating
                 that the corresponding registration update was
                 accepted), since system was last restarted."
        REFERENCE
                 "Refer to TIA/EIA international telecommunications
                  organization standard TR 45.4 for A10 session update
                  message and TR 45.6 for Accounting Model."
        ::= { cCdmaPcfSoRpUpdStatsEntry 5 }

cCdmaPcfSoRpUpdDeniedReqs OBJECT-TYPE
        SYNTAX      ZeroBasedCounter32
        MAX-ACCESS  read-only
        STATUS      current
        DESCRIPTION
                "Total number of A11 registration acknowledgements
                 received with the Status field set to non-zero
                 indicating that the corresponding registration update
                 was denied, since system was last restarted."
        REFERENCE
                 "Refer to TIA/EIA international telecommunications
                  organization standard TR 45.4 for A10 session update
                  message and TR 45.6 for Accounting Model."
        ::= { cCdmaPcfSoRpUpdStatsEntry 6 }

cCdmaPcfSoRpUpdNotAckedReqs OBJECT-TYPE
        SYNTAX      ZeroBasedCounter32
        MAX-ACCESS  read-only
        STATUS      current
        DESCRIPTION
                "Total number of A11 registration updates sent,
                 for which no corresponding A11 registration
                 acknowledgements received, since system was last
                 restarted."
        REFERENCE
                 "Refer to TIA/EIA international telecommunications
                  organization standard TR 45.4 for A10 session update
                  message and TR 45.6 for Accounting Model."
        ::= { cCdmaPcfSoRpUpdStatsEntry 7 }

cCdmaPcfSoRpUpdInitTxdReqs OBJECT-TYPE
        SYNTAX      ZeroBasedCounter32
        MAX-ACCESS  read-only
        STATUS      current
        DESCRIPTION
                "Total number of initial A11 registration updates
                 sent, excluding the re-transmitted A11 registration
                 updates, since system was last restarted."
        REFERENCE
                 "Refer to TIA/EIA international telecommunications
                  organization standard TR 45.4 for A10 session update
                  message and TR 45.6 for Accounting Model."
        ::= { cCdmaPcfSoRpUpdStatsEntry 8 }

cCdmaPcfSoRpUpdReTxdReqs OBJECT-TYPE
        SYNTAX      ZeroBasedCounter32
        MAX-ACCESS  read-only
        STATUS      current
        DESCRIPTION
                "Total number of re-transmitted A11 registration
                 updates, since system was last restarted."
        REFERENCE
                 "Refer to TIA/EIA international telecommunications
                  organization standard TR 45.4 for A10 session update
                  message and TR 45.6 for Accounting Model."
        ::= { cCdmaPcfSoRpUpdStatsEntry 9 }

cCdmaPcfSoRpUpdRcvdAcks OBJECT-TYPE
        SYNTAX      ZeroBasedCounter32
        MAX-ACCESS  read-only
        STATUS      current
        DESCRIPTION
                "Total number of A11 registration acknowledgements
                 received, since system was last restarted."
        REFERENCE
                 "Refer to TIA/EIA international telecommunications
                  organization standard TR 45.4 for A10 session update
                  message and TR 45.6 for Accounting Model."
        ::= { cCdmaPcfSoRpUpdStatsEntry 10 }

cCdmaPcfSoRpUpdDiscardedAcks OBJECT-TYPE
        SYNTAX      ZeroBasedCounter32
        MAX-ACCESS  read-only
        STATUS      current
        DESCRIPTION
                "Total number of A11 registration acknowledgements
                 discarded, since system was last restarted."
        REFERENCE
                 "Refer to TIA/EIA international telecommunications
                  organization standard TR 45.4 for A10 session update
                  message and TR 45.6 for Accounting Model."
        ::= { cCdmaPcfSoRpUpdStatsEntry 11 }

cCdmaPcfSoRpUpdRpLifeExpReqs OBJECT-TYPE
        SYNTAX      ZeroBasedCounter32
        MAX-ACCESS  read-only
        STATUS      current
        DESCRIPTION
                "Total number of initial A11 registration updates
                 sent due to RP lifetime expiry since system was
                 last restarted."
        REFERENCE
                 "Refer to TIA/EIA international telecommunications
                  organization standard TR 45.4 for A10 session update
                  message and TR 45.6 for Accounting Model."
        ::= { cCdmaPcfSoRpUpdStatsEntry 12 }

cCdmaPcfSoRpUpdPPPtermReqs OBJECT-TYPE
        SYNTAX      ZeroBasedCounter32
        MAX-ACCESS  read-only
        STATUS      current
        DESCRIPTION
                "Total number of initial A11 registration updates
                 sent as a result of PPP termination, since system
                 was last restarted."
        REFERENCE
                 "Refer to TIA/EIA international telecommunications
                  organization standard TR 45.4 for A10 session update
                  message and TR 45.6 for Accounting Model."
        ::= { cCdmaPcfSoRpUpdStatsEntry 13 }

cCdmaPcfSoRpUpdOtherReaReqs OBJECT-TYPE
        SYNTAX      ZeroBasedCounter32
        MAX-ACCESS  read-only
        STATUS      current
        DESCRIPTION
                "Total number of initial A11 registration updates
                 sent due to reasons other than RP lifetime expiry,
                 or PPP termination, since system was last restarted."
        REFERENCE
                 "Refer to TIA/EIA international telecommunications
                  organization standard TR 45.4 for A10 session update
                  message and TR 45.6 for Accounting Model."
        ::= { cCdmaPcfSoRpUpdStatsEntry 14 }

cCdmaPcfSoRpUpdReaUnSpecFails OBJECT-TYPE
        SYNTAX      ZeroBasedCounter32
        MAX-ACCESS  read-only
        STATUS      current
        DESCRIPTION
                "The number of update registrations failed for
                 unspecified reason since system was last restarted."
        REFERENCE
                 "Refer to TIA/EIA international telecommunications
                  organization standard TR 45.4 for details about A10
                  session setup errors."
        ::= { cCdmaPcfSoRpUpdStatsEntry 15 }

cCdmaPcfSoRpUpdAdmnFails OBJECT-TYPE
        SYNTAX      ZeroBasedCounter32
        MAX-ACCESS  read-only
        STATUS      current
        DESCRIPTION
                "The number of update registrations failed due to
                 administrative prohibition since system was last
                 restarted."
        REFERENCE
                 "Refer to TIA/EIA international telecommunications
                  organization standard TR 45.4 for details about A10
                  session setup errors."
        ::= { cCdmaPcfSoRpUpdStatsEntry 16 }

cCdmaPcfSoRpUpdMNAuthFails OBJECT-TYPE
        SYNTAX      ZeroBasedCounter32
        MAX-ACCESS  read-only
        STATUS      current
        DESCRIPTION
                "The number of update registrations failed due to MN
                 authentication failure since system was last
                 restarted."
        REFERENCE
                 "Refer to TIA/EIA international telecommunications
                  organization standard TR 45.4 for details about A10
                  session setup errors."
        ::= { cCdmaPcfSoRpUpdStatsEntry 17 }

cCdmaPcfSoRpUpdIdMismatFails OBJECT-TYPE
        SYNTAX      ZeroBasedCounter32
        MAX-ACCESS  read-only
        STATUS      current
        DESCRIPTION
                "The number of registrations failed due to registration
                 identity mismatch since system was last restarted."
        REFERENCE
                 "Refer to TIA/EIA international telecommunications
                  organization standard TR 45.4 for details about A10
                  session setup errors."
        ::= { cCdmaPcfSoRpUpdStatsEntry 18 }

cCdmaPcfSoRpUpdBadReqFails OBJECT-TYPE
        SYNTAX      ZeroBasedCounter32
        MAX-ACCESS  read-only
        STATUS      current
        DESCRIPTION
                "The number of update registrations failed due to
                 poorly formed request since system was last restarted."
        REFERENCE
                 "Refer to TIA/EIA international telecommunications
                  organization standard TR 45.4 for details about A10
                  session setup errors."
        ::= { cCdmaPcfSoRpUpdStatsEntry 19 }

cCdmaSoRpUpdPcfHandoffs OBJECT-TYPE
        SYNTAX      ZeroBasedCounter32
        MAX-ACCESS  read-only
        STATUS      current
        DESCRIPTION
                "The number of update registrations sent as a 
                 result of inter pcf handoffs, since system was
                 last restarted."
        ::= { cCdmaPcfSoRpUpdStatsEntry 20 }

cCdmaSoRpUpdHandoffNotAckedReqs OBJECT-TYPE
        SYNTAX      ZeroBasedCounter32
        MAX-ACCESS  read-only
        STATUS      current
        DESCRIPTION
                "Total number of A11 Registration Updates (sent
                 as the result of inter PCF handoffs), for which no
                 corresponding A11  Registration Acknowledgements 
                 received, since system was last restarted."
        ::= { cCdmaPcfSoRpUpdStatsEntry 21 }

cCdmaSoRpUpdHandoffReceivedAcks OBJECT-TYPE
        SYNTAX      ZeroBasedCounter32
        MAX-ACCESS  read-only
        STATUS      current
        DESCRIPTION
                "Total number of A11 Registration Acknowledgements
                 received for the A11 Registration Updates sent as
                 the result of inter PCF handoffs, since system was
                 last restarted. "
        ::= { cCdmaPcfSoRpUpdStatsEntry 22 }

cCdmaSoRpUpdHandoffAcceptedReqs OBJECT-TYPE
        SYNTAX      ZeroBasedCounter32
        MAX-ACCESS  read-only
        STATUS      current
        DESCRIPTION
                "Total number of A11 Registration Acknowledgements
                 received with the Status field set to zero (indicating
                 that the corresponding Registration Update was
                 accepted), since system was last restarted."
        REFERENCE
                 "Refer to TIA/EIA international telecommunications
                  organization standard TR 45.4 for A10 session update
                  message and TR 45.6 for Accounting Model."
        ::= { cCdmaPcfSoRpUpdStatsEntry 23 }

cCdmaSoRpUpdHandoffDeniedReqs OBJECT-TYPE
        SYNTAX      ZeroBasedCounter32
        MAX-ACCESS  read-only
        STATUS      current
        DESCRIPTION
                "Total number of A11 Registration Acknowledgements
                 received with the Status field set to non-zero
                 indicating that the corresponding Registration Update
                 was denied, since system was last restarted."
        REFERENCE
                 "Refer to TIA/EIA international telecommunications
                  organization standard TR 45.4 for A10 session update
                  message and TR 45.6 for Accounting Model."
        ::= { cCdmaPcfSoRpUpdStatsEntry 24 }

cCdmaSoRpUpdHandoffDiscardedAcks OBJECT-TYPE
        SYNTAX      ZeroBasedCounter32
        MAX-ACCESS  read-only
        STATUS      current
        DESCRIPTION
                "Total number of A11 Registration Acknowledgements
                 discarded, since system was last restarted."
        ::= { cCdmaPcfSoRpUpdStatsEntry 25 }
           
cCdmaSoRpUpdHandoffInitTxdReqs OBJECT-TYPE
        SYNTAX      ZeroBasedCounter32
        MAX-ACCESS  read-only
        STATUS      current
        DESCRIPTION
                "Total number of initial A11 Registration Updates
                 sent as the result of inter PCF handoffs, excluding
                 the re-transmitted A11 Registration Updates, since
                 system was last restarted."
        ::= { cCdmaPcfSoRpUpdStatsEntry 26 }

cCdmaSoRpUpdHandoffReTxdReqs OBJECT-TYPE
        SYNTAX      ZeroBasedCounter32
        MAX-ACCESS  read-only
        STATUS      current
        DESCRIPTION
                "Total number of re-transmitted A11 Registration
                 Updates as the initial Registration Update (sent
                 as a result of inter PCF handoffs) was not acked
                 or denied, since system was last restarted."
        ::= { cCdmaPcfSoRpUpdStatsEntry 27 }
            
cCdmaSoRpUpdHandoffReaUnSpecFails OBJECT-TYPE
        SYNTAX      ZeroBasedCounter32
        MAX-ACCESS  read-only
        STATUS      current
        DESCRIPTION
                "The number of update registrations failed for
                 unspecified reason since system was last
                 restarted.  The update is sent as a result of
                 inter PCF handoff."
        ::= { cCdmaPcfSoRpUpdStatsEntry 28 }
            
cCdmaSoRpUpdHandoffAdmProhibFails OBJECT-TYPE
        SYNTAX      ZeroBasedCounter32
        MAX-ACCESS  read-only
        STATUS      current
        DESCRIPTION
                "The number of update registrations failed due to
                 administrative prohibition since system was last
                 restarted.  The update is sent as a result of
                 inter PCF handoff."
        ::= { cCdmaPcfSoRpUpdStatsEntry 29 }

cCdmaSoRpUpdHandoffMNAuthenFails OBJECT-TYPE
        SYNTAX      ZeroBasedCounter32
        MAX-ACCESS  read-only
        STATUS      current
        DESCRIPTION
                "The number of update registrations failed due 
                 to MN authentication failure since system was 
                 last restarted.  The update is sent as a result
                 of inter PCF handoff."
        ::= { cCdmaPcfSoRpUpdStatsEntry 30 }
            
cCdmaSoRpUpdHandoffIdMismatchFails OBJECT-TYPE
        SYNTAX      ZeroBasedCounter32
        MAX-ACCESS  read-only
        STATUS      current
        DESCRIPTION
                "The number of registrations failed due to registration
                 identity mismatch since system was last restarted.
                 The update is sent as a result of inter PCF handoff."
        ::= { cCdmaPcfSoRpUpdStatsEntry 31 }
            
cCdmaSoRpUpdHandoffBadReqFails OBJECT-TYPE
        SYNTAX      ZeroBasedCounter32
        MAX-ACCESS  read-only
        STATUS      current
        DESCRIPTION
                "The number of update registrations failed due to
                 poorly formed request since system was last 
                 restarted.  The update is sent as a result of inter
                 PCF handoff."
        ::= { cCdmaPcfSoRpUpdStatsEntry 32 }

-- *******************************************************************
-- * CDMA PDSN PCF and Service Option based RP Session Update 
-- * Statistics 
-- *******************************************************************

cCdmaPcfSoRpSessUpdStatsTable       OBJECT-TYPE
         SYNTAX      SEQUENCE OF CCdmaPcfSoRpSessUpdStatsEntry
         MAX-ACCESS  not-accessible
         STATUS      current
         DESCRIPTION
                 "A table containing RP update statistics such as
                  RP updates sent, acks received etc., grouped and
                  index on the basis of PCF's IP address and the
                  service option."
         ::= { cCdmaPcfSoRpSessUpdStats 1 }

cCdmaPcfSoRpSessUpdStatsEntry   OBJECT-TYPE
         SYNTAX      CCdmaPcfSoRpSessUpdStatsEntry
         MAX-ACCESS  not-accessible
         STATUS      current
         DESCRIPTION
                 "The RP update statistics pertaining to a unique
                  combination of PCF and service option."
         INDEX { cCdmaPcfSoRpSessUpdIpAddrType,
                 cCdmaPcfSoRpSessUpdIpAddr, 
                 cCdmaPcfSoRpSessUpdServiceOption }
         ::= { cCdmaPcfSoRpSessUpdStatsTable 1 }

CCdmaPcfSoRpSessUpdStatsEntry ::=
         SEQUENCE {
             cCdmaPcfSoRpSessUpdIpAddrType           InetAddressType,
             cCdmaPcfSoRpSessUpdIpAddr               InetAddress,
             cCdmaPcfSoRpSessUpdServiceOption        CCdmaServiceOption,
             cCdmaPcfSoRpSessUpdTxdReqs              ZeroBasedCounter32,
             cCdmaPcfSoRpSessUpdAcptdReqs            ZeroBasedCounter32,
             cCdmaPcfSoRpSessUpdDeniedReqs           ZeroBasedCounter32,
             cCdmaPcfSoRpSessUpdNotAckedReqs         ZeroBasedCounter32,
             cCdmaPcfSoRpSessUpdInitTxdReqs          ZeroBasedCounter32,
             cCdmaPcfSoRpSessUpdReTxdReqs            ZeroBasedCounter32,
             cCdmaPcfSoRpSessUpdRcvdAcks             ZeroBasedCounter32,
             cCdmaPcfSoRpSessUpdDiscardedAcks        ZeroBasedCounter32,
             cCdmaPcfSoRpSessUpdAlwaysOn             ZeroBasedCounter32,
             cCdmaPcfSoRpSessUpdRNPDIT               ZeroBasedCounter32,
             cCdmaPcfSoRpSessUpdParamNotUpdated      ZeroBasedCounter32,
             cCdmaPcfSoRpSessUpdReaUnSpecFails       ZeroBasedCounter32,
             cCdmaPcfSoRpSessUpdMNAuthFails          ZeroBasedCounter32,
             cCdmaPcfSoRpSessUpdIdMismatFails        ZeroBasedCounter32,
             cCdmaPcfSoRpSessUpdBadReqFails          ZeroBasedCounter32
         }             

cCdmaPcfSoRpSessUpdIpAddrType   OBJECT-TYPE
         SYNTAX      InetAddressType
         MAX-ACCESS  not-accessible
         STATUS      current
         DESCRIPTION
                 "Represents the type of the address specified by
                  cCdmaPcfSoRpSessUpdIpAddr."
         ::= { cCdmaPcfSoRpSessUpdStatsEntry 1 }

cCdmaPcfSoRpSessUpdIpAddr   OBJECT-TYPE
         SYNTAX      InetAddress
         MAX-ACCESS  not-accessible
         STATUS      current
         DESCRIPTION
                 "The IP address of the PCF that serves
                  the mobile node."
         ::= { cCdmaPcfSoRpSessUpdStatsEntry 2 }
         
cCdmaPcfSoRpSessUpdServiceOption OBJECT-TYPE
         SYNTAX      CCdmaServiceOption
         MAX-ACCESS  not-accessible
         STATUS      current
         DESCRIPTION
                 "A packet data service option, specifies a means
                  between MS and RN to establish and maintain cdma2000
                  traffic channels for packet data service."
         ::= { cCdmaPcfSoRpSessUpdStatsEntry 3 }

cCdmaPcfSoRpSessUpdTxdReqs OBJECT-TYPE
        SYNTAX      ZeroBasedCounter32
        MAX-ACCESS  read-only
        STATUS      current
        DESCRIPTION
                "Total number of A11 session updates transmitted
                 since system was last restarted."
        REFERENCE
                 "Refer to TIA/EIA international telecommunications
                  organization standard TR 45.4 for A10 session update
                  message and TR 45.6 for Accounting Model."
        ::= { cCdmaPcfSoRpSessUpdStatsEntry 4 }

cCdmaPcfSoRpSessUpdAcptdReqs OBJECT-TYPE
        SYNTAX      ZeroBasedCounter32
        MAX-ACCESS  read-only
        STATUS      current
        DESCRIPTION
                "Total number of A11 session update acknowledgements
                 received with the Status field set to zero (indicating
                 that the corresponding registration update was
                 accepted), since system was last restarted."
        REFERENCE
                 "Refer to TIA/EIA international telecommunications
                  organization standard TR 45.4 for A10 session update
                  message and TR 45.6 for Accounting Model."
        ::= { cCdmaPcfSoRpSessUpdStatsEntry 5 }

cCdmaPcfSoRpSessUpdDeniedReqs OBJECT-TYPE
        SYNTAX      ZeroBasedCounter32
        MAX-ACCESS  read-only
        STATUS      current
        DESCRIPTION
                "Total number of A11 session update acknowledgements
                 received with the Status field set to non-zero
                 indicating that the corresponding registration update
                 was denied, since system was last restarted."
        REFERENCE
                 "Refer to TIA/EIA international telecommunications
                  organization standard TR 45.4 for A10 session update
                  message and TR 45.6 for Accounting Model."
        ::= { cCdmaPcfSoRpSessUpdStatsEntry 6 }

cCdmaPcfSoRpSessUpdNotAckedReqs OBJECT-TYPE
        SYNTAX      ZeroBasedCounter32
        MAX-ACCESS  read-only
        STATUS      current
        DESCRIPTION
                "Total number of A11 session updates sent,
                 for which no corresponding A11 registration
                 acknowledgements received, since system was last
                 restarted."
        REFERENCE
                 "Refer to TIA/EIA international telecommunications
                  organization standard TR 45.4 for A10 session update
                  message and TR 45.6 for Accounting Model."
        ::= { cCdmaPcfSoRpSessUpdStatsEntry 7 }

cCdmaPcfSoRpSessUpdInitTxdReqs OBJECT-TYPE
        SYNTAX      ZeroBasedCounter32
        MAX-ACCESS  read-only
        STATUS      current
        DESCRIPTION
                "Total number of initial A11 session updates
                 sent, excluding the re-transmitted A11 registration
                 updates, since system was last restarted."
        REFERENCE
                 "Refer to TIA/EIA international telecommunications
                  organization standard TR 45.4 for A10 session update
                  message and TR 45.6 for Accounting Model."
        ::= { cCdmaPcfSoRpSessUpdStatsEntry 8 }

cCdmaPcfSoRpSessUpdReTxdReqs OBJECT-TYPE
        SYNTAX      ZeroBasedCounter32
        MAX-ACCESS  read-only
        STATUS      current
        DESCRIPTION
                "Total number of re-transmitted A11 session
                 updates, since system was last restarted."
        REFERENCE
                 "Refer to TIA/EIA international telecommunications
                  organization standard TR 45.4 for A10 session update
                  message and TR 45.6 for Accounting Model."
        ::= { cCdmaPcfSoRpSessUpdStatsEntry 9 }

cCdmaPcfSoRpSessUpdRcvdAcks OBJECT-TYPE
        SYNTAX      ZeroBasedCounter32
        MAX-ACCESS  read-only
        STATUS      current
        DESCRIPTION
                "Total number of A11 session acknowledgements
                 received, since system was last restarted."
        REFERENCE
                 "Refer to TIA/EIA international telecommunications
                  organization standard TR 45.4 for A10 session update
                  message and TR 45.6 for Accounting Model."
        ::= { cCdmaPcfSoRpSessUpdStatsEntry 10 }

cCdmaPcfSoRpSessUpdDiscardedAcks OBJECT-TYPE
        SYNTAX      ZeroBasedCounter32
        MAX-ACCESS  read-only
        STATUS      current
        DESCRIPTION
                "Total number of A11 session update acknowledgements
                 discarded, since system was last restarted."
        REFERENCE
                 "Refer to TIA/EIA international telecommunications
                  organization standard TR 45.4 for A10 session update
                  message and TR 45.6 for Accounting Model."
        ::= { cCdmaPcfSoRpSessUpdStatsEntry 11 }

cCdmaPcfSoRpSessUpdAlwaysOn OBJECT-TYPE
        SYNTAX      ZeroBasedCounter32
        MAX-ACCESS  read-only
        STATUS      current
        DESCRIPTION
                "Total number of initial A11 registration updates
                 sent due to Always On downloaded since system was
                 last restarted."
        REFERENCE
                 "Refer to TIA/EIA international telecommunications
                  organization standard TR 45.4 for A10 session update
                  message and TR 45.6 for Accounting Model."
        ::= { cCdmaPcfSoRpSessUpdStatsEntry 12 }

cCdmaPcfSoRpSessUpdRNPDIT OBJECT-TYPE
        SYNTAX      ZeroBasedCounter32
        MAX-ACCESS  read-only
        STATUS      current
        DESCRIPTION
                "Total number of initial A11 registration updates
                 sent due to TNPDIT downloaded, since system
                 was last restarted."
        REFERENCE
                 "Refer to TIA/EIA international telecommunications
                  organization standard TR 45.4 for A10 session update
                  message and TR 45.6 for Accounting Model."
        ::= { cCdmaPcfSoRpSessUpdStatsEntry 13 }

cCdmaPcfSoRpSessUpdParamNotUpdated OBJECT-TYPE
        SYNTAX      ZeroBasedCounter32
        MAX-ACCESS  read-only
        STATUS      current
        DESCRIPTION
                "The number of session update failed for session
                 parameter not updated reason since system was last
                 restarted."
        REFERENCE
                 "Refer to TIA/EIA international telecommunications
                  organization standard TR 45.4 for A10 session update
                  message and TR 45.6 for Accounting Model."
        ::= { cCdmaPcfSoRpSessUpdStatsEntry 14 }

cCdmaPcfSoRpSessUpdReaUnSpecFails OBJECT-TYPE
        SYNTAX      ZeroBasedCounter32
        MAX-ACCESS  read-only
        STATUS      current
        DESCRIPTION
                "The number of session update failed for
                 unspecified reason since system was last restarted."
        REFERENCE
                 "Refer to TIA/EIA international telecommunications
                  organization standard TR 45.4 for details about A10
                  session setup errors."
        ::= { cCdmaPcfSoRpSessUpdStatsEntry 15 }

cCdmaPcfSoRpSessUpdMNAuthFails OBJECT-TYPE
        SYNTAX      ZeroBasedCounter32
        MAX-ACCESS  read-only
        STATUS      current
        DESCRIPTION
                "The number of session update failed due to MN
                 authentication failure since system was last
                 restarted."
        REFERENCE
                 "Refer to TIA/EIA international telecommunications
                  organization standard TR 45.4 for details about A10
                  session setup errors."
        ::= { cCdmaPcfSoRpSessUpdStatsEntry 16 }

cCdmaPcfSoRpSessUpdIdMismatFails OBJECT-TYPE
        SYNTAX      ZeroBasedCounter32
        MAX-ACCESS  read-only
        STATUS      current
        DESCRIPTION
                "The number of session update failed due to registration
                 identity mismatch since system was last restarted."
        REFERENCE
                 "Refer to TIA/EIA international telecommunications
                  organization standard TR 45.4 for details about A10
                  session setup errors."
        ::= { cCdmaPcfSoRpSessUpdStatsEntry 17 }

cCdmaPcfSoRpSessUpdBadReqFails OBJECT-TYPE
        SYNTAX      ZeroBasedCounter32
        MAX-ACCESS  read-only
        STATUS      current
        DESCRIPTION
                "The number of session update failed due to
                 poorly formed request since system was last restarted."
        REFERENCE
                 "Refer to TIA/EIA international telecommunications
                  organization standard TR 45.4 for details about A10
                  session setup errors."
        ::= { cCdmaPcfSoRpSessUpdStatsEntry 18 }
        
-- ******************************************************************
-- * CDMA PPP Setup Counters
-- ******************************************************************

cCdmaPcfSoPppSetupStatsTable       OBJECT-TYPE
         SYNTAX      SEQUENCE OF CCdmaExtPcfSoPppSetupStatsEntry
         MAX-ACCESS  not-accessible
         STATUS      current
         DESCRIPTION
                 "A table containing PPP negotiation statistics such as
                  PPP negotiations initiated, negotiation successes 
                  etc., grouped and index on the basis of PCF's IP 
                  address and the service option."
         ::= { cCdmaPcfSoPppSetupStats 1 }

cCdmaPcfSoPppSetupStatsEntry   OBJECT-TYPE
         SYNTAX      CCdmaExtPcfSoPppSetupStatsEntry
         MAX-ACCESS  not-accessible
         STATUS      current
         DESCRIPTION
                 "The PPP negotiation statistics pertaining to a unique
                  combination of PCF and service option."
         INDEX { cCdmaPcfSoPppSetupIpAddrType,
                 cCdmaPcfSoPppSetupIpAddr,
                 cCdmaPcfSoPppServiceOption }
         ::= { cCdmaPcfSoPppSetupStatsTable 1 }

CCdmaExtPcfSoPppSetupStatsEntry ::=
         SEQUENCE {
             cCdmaPcfSoPppSetupIpAddrType       InetAddressType,
             cCdmaPcfSoPppSetupIpAddr           InetAddress,
             cCdmaPcfSoPppServiceOption         CCdmaServiceOption,
             cCdmaPcfSoPppCurrentConns          Gauge32,
             cCdmaPcfSoPppConnInitiateReqs      ZeroBasedCounter32,
             cCdmaPcfSoPppConnSuccesses         ZeroBasedCounter32,
             cCdmaPcfSoPppConnFails             ZeroBasedCounter32,
             cCdmaPcfSoPppConnAborts            ZeroBasedCounter32
         }

cCdmaPcfSoPppSetupIpAddrType   OBJECT-TYPE
         SYNTAX      InetAddressType
         MAX-ACCESS  not-accessible
         STATUS      current
         DESCRIPTION
                 "Represents the type of the address specified by
                  cCdmaPcfSoPppSetupIpAddr."
         ::= { cCdmaPcfSoPppSetupStatsEntry 1 }

cCdmaPcfSoPppSetupIpAddr   OBJECT-TYPE
         SYNTAX      InetAddress
         MAX-ACCESS  not-accessible
         STATUS      current
         DESCRIPTION
                 "The IP address of the PCF that serves the Mobile
                  Node."
         ::= { cCdmaPcfSoPppSetupStatsEntry 2 }
         
cCdmaPcfSoPppServiceOption OBJECT-TYPE         
         SYNTAX      CCdmaServiceOption
         MAX-ACCESS  not-accessible
         STATUS      current
         DESCRIPTION
                 "A packet data service option, specifies a means
                  between MS and RN to establish and maintain cdma2000
                  traffic channels for packet data service."
         ::= { cCdmaPcfSoPppSetupStatsEntry 3 }

cCdmaPcfSoPppCurrentConns OBJECT-TYPE
        SYNTAX      Gauge32
        MAX-ACCESS  read-only
        STATUS      current
        DESCRIPTION
                "Total number of currently active PPP connections."
        REFERENCE
                 "[1] RFC-1661 'The Point-to-Point Protocol (PPP)', 
                      W. Simpson.
                  [2] TIA/EIA standard TR 45.4 for details about 
                      A10/A11 (R-P) interface."
        ::= { cCdmaPcfSoPppSetupStatsEntry 4 }

cCdmaPcfSoPppConnInitiateReqs OBJECT-TYPE
        SYNTAX      ZeroBasedCounter32
        MAX-ACCESS  read-only
        STATUS      current
        DESCRIPTION
                "Total number of PPP connection initiate requests
                 sent out since system was last restarted."
        REFERENCE
                 "[1] RFC-1661 'The Point-to-Point Protocol (PPP)', 
                      W. Simpson.
                  [2] TIA/EIA standard TR 45.4 for details about 
                      A10/A11 (R-P) interface."
        ::= { cCdmaPcfSoPppSetupStatsEntry 5 }

cCdmaPcfSoPppConnSuccesses OBJECT-TYPE
        SYNTAX      ZeroBasedCounter32
        MAX-ACCESS  read-only
        STATUS      current
        DESCRIPTION
                "Total number of PPP connections that have been 
                 successfully brought to active state since system
                 was last restarted."
        REFERENCE
                 "[1] RFC-1661 'The Point-to-Point Protocol (PPP)', 
                      W. Simpson.
                  [2] TIA/EIA standard TR 45.4 for details about 
                      A10/A11 (R-P) interface."
        ::= { cCdmaPcfSoPppSetupStatsEntry 6 }

cCdmaPcfSoPppConnFails OBJECT-TYPE
        SYNTAX      ZeroBasedCounter32
        MAX-ACCESS  read-only
        STATUS      current
        DESCRIPTION
                "The number of PPP connection setup request failed since
                 system was last restarted."
        REFERENCE
                 "[1] RFC-1661 'The Point-to-Point Protocol (PPP)', 
                      W. Simpson.
                  [2] TIA/EIA standard TR 45.4 for details about 
                      A10/A11 (R-P) interface."
        ::= { cCdmaPcfSoPppSetupStatsEntry 7 }
        
cCdmaPcfSoPppConnAborts OBJECT-TYPE        
        SYNTAX      ZeroBasedCounter32
        MAX-ACCESS  read-only
        STATUS      current
        DESCRIPTION
                "Total number of PPP negotiations terminated
                 prematurely, due to reasons such as MN poweroff,
                     since system was last restarted."
        REFERENCE
                 "[1] RFC-1661 'The Point-to-Point Protocol (PPP)', 
                      W. Simpson.
                  [2] TIA/EIA standard TR 45.4 for details about 
                      A10/A11 (R-P) interface."
        ::= { cCdmaPcfSoPppSetupStatsEntry 8 }      

-- ******************************************************************
-- PDSN configuration:
-- ******************************************************************
cCdmaSessionHighThreshold  OBJECT-TYPE
         SYNTAX      Unsigned32
         MAX-ACCESS  read-write
         STATUS      current
         DESCRIPTION
                 "A threshold marking the high number of allowed 
                  sessions. Agent generates a notification when 
                  this threshold is reached during call setup."
         ::= { cCdmaThresholdConfig 1 }


cCdmaSessionLowThreshold  OBJECT-TYPE
         SYNTAX      Unsigned32
         MAX-ACCESS  read-write
         STATUS      current
         DESCRIPTION
                 "A threshold marking the low number of allowed 
                  sessions. Agent generates a notification when
                  this threshold is reached during call release."
         ::= { cCdmaThresholdConfig 2 }

-- *******************************************************************
-- A PDSN cluster
-- *******************************************************************
cCdmaClusterType OBJECT-TYPE
         SYNTAX      INTEGER {
                       nonCluster(0),
                       peerToPeer(1),
                       controllerMember(2)
                     }
         MAX-ACCESS  read-only
         STATUS      current
         DESCRIPTION
                 "The type of this PDSN cluster. 
                    - 'nonCluster' indicates cluster is not provisioned.
                    - 'peerToPeer' indicates cluster type is peer-to-
                      peer.
                    - 'controllerMember' indicates cluster type is 
                      controller-member type." 
         ::= { cCdmaClusterCommon 1 }

cCdmaClusterRole OBJECT-TYPE
         SYNTAX      INTEGER {
                       notApply(0),
                       controller(1),
                       member(2)
                     }
         MAX-ACCESS  read-only
         STATUS      current
         DESCRIPTION
                 "The role this PDSN plays within a controller-member
                  type of cluster:
                    - 'notApply' indicates this PDSN does not play
                      any cluster role. PDSN has this role if the
                      cCdmaClusterType is not controller-member.
                    - 'controller' indicates this PDSN is the controller
                      of this cluster.
                    - 'member' indicates this PDSN is a member of
                      this cluster."
         ::= { cCdmaClusterCommon 2 }

-- ************************************************************************
-- PDSN cluster member related variables:
-- ************************************************************************
cCdmaClusterTotalControllers OBJECT-TYPE
         SYNTAX      Gauge32
         MAX-ACCESS  read-only
         STATUS      current
         DESCRIPTION
                 "The total number of cluster controllers within this
                  cluster."
         ::= { cCdmaClusterMemberInfo 1 }

cCdmaClusterCtrlTable OBJECT-TYPE
         SYNTAX      SEQUENCE OF CCdmaClusterCtrlEntry
         MAX-ACCESS  not-accessible
         STATUS      current
         DESCRIPTION
                 "A list of cluster controllers maintained by a PDSN
                  cluster member. An entry is created when a cluster
                  controller is added through provisioning command.
                  An entry is deleted when a cluster controller is 
                  removed through provisioning command."
         ::= { cCdmaClusterMemberInfo 2 }

cCdmaClusterCtrlEntry OBJECT-TYPE
         SYNTAX    CCdmaClusterCtrlEntry
         MAX-ACCESS  not-accessible
         STATUS      current
         DESCRIPTION
                 "A conceptual row in cluster controller table, which
                  represents a cluster controller of a particular 
                  InetAddress type and address."
         INDEX { cCdmaClusterCtrlAddressType,cCdmaClusterCtrlAddress }
         ::= { cCdmaClusterCtrlTable 1 }

CCdmaClusterCtrlEntry ::=
         SEQUENCE {
             cCdmaClusterCtrlAddressType InetAddressType,
             cCdmaClusterCtrlAddress     InetAddress,
             cCdmaClusterCtrlStatus      INTEGER
         }

cCdmaClusterCtrlAddressType OBJECT-TYPE
         SYNTAX      InetAddressType
         MAX-ACCESS  not-accessible
         STATUS      current
         DESCRIPTION
                 "This is the IP address type of a particular 
                  controller and is used as index (combine with
                  cCdmaClusterCtrlAddress) to identify a unique
                  cluster controller entry."
         ::= { cCdmaClusterCtrlEntry 1 }

cCdmaClusterCtrlAddress OBJECT-TYPE
         SYNTAX      InetAddress
         MAX-ACCESS  not-accessible
         STATUS      current
         DESCRIPTION
                 "This is the IP address of a particular controller
                  and is used as index (combine with cCdmaCluster-
                  CtrlAddressType) to identify a unique cluster 
                  controller entry."
         ::= { cCdmaClusterCtrlEntry 2 }

cCdmaClusterCtrlStatus OBJECT-TYPE
         SYNTAX      INTEGER {
                        notConfigured(1),
                        configured(2),
                        alive(3)
                     }
         MAX-ACCESS  read-only
         STATUS      current
         DESCRIPTION
                 "The operational status of the cluster controller
                  maintained by the member."
         ::= { cCdmaClusterCtrlEntry 3 }

-- ************************************************************************
-- PDSN cluster controller related variables:
-- ************************************************************************
cCdmaClusterTotalSessions OBJECT-TYPE
         SYNTAX      Gauge32
         MAX-ACCESS  read-only
         STATUS      current
         DESCRIPTION
                 "The total number of session records in PDSN cluster 
                  controller."
         ::= { cCdmaClusterControllerInfo 1 }

cCdmaClusterSessHighThreshold  OBJECT-TYPE
         SYNTAX      Unsigned32
         MAX-ACCESS  read-write
         STATUS      current
         DESCRIPTION
                 "A threshold marking the high number of allowed 
                  sessions within a PDSN cluster controller.
                  Notification will be generated when this threshold
                  is reached during call setup."
         ::= { cCdmaClusterControllerInfo 2 }

cCdmaClusterSessLowThreshold  OBJECT-TYPE
         SYNTAX      Unsigned32
         MAX-ACCESS  read-write
         STATUS      current
         DESCRIPTION
                 "A threshold marking the low number of allowed
                  sessions within a PDSN cluster controller.
                  Notification will be generated when this threshold
                  is reached during call release."
         ::= { cCdmaClusterControllerInfo 3 }

cCdmaClusterTotalMembers OBJECT-TYPE
         SYNTAX      Gauge32
         MAX-ACCESS  read-only
         STATUS      current
         DESCRIPTION
                 "The total number of member records in PDSN cluster 
                  controller."
         ::= { cCdmaClusterControllerInfo 4 }

cCdmaClusterMemberTable OBJECT-TYPE
         SYNTAX      SEQUENCE OF CCdmaClusterMemberEntry
         MAX-ACCESS  not-accessible
         STATUS      current
         DESCRIPTION
                 "A list of cluster members maintained by a PDSN
                  cluster controller. An entry is created when a 
                  cluster member is added through provisioning 
                  command or auto-discovered. An entry is deleted when
                  a cluster member is removed through provisioning 
                  command or found dead by auto-discovering."
         ::= { cCdmaClusterControllerInfo 5 }

cCdmaClusterMemberEntry OBJECT-TYPE
         SYNTAX    CCdmaClusterMemberEntry
         MAX-ACCESS  not-accessible
         STATUS      current
         DESCRIPTION
                 "A conceptual row in cCdmaClusterMemberTable table,
                  which represents a PDSN cluster member of particular
                  InetAddress type and address."
         INDEX { cCdmaClusterMemberAddressType,
                 cCdmaClusterMemberAddress }
         ::= { cCdmaClusterMemberTable 1 }

CCdmaClusterMemberEntry ::=
         SEQUENCE {
             cCdmaClusterMemberAddressType InetAddressType,
             cCdmaClusterMemberAddress     InetAddress,
             cCdmaClusterMemberStatus      INTEGER,
             cCdmaClusterMemberLoad        Unsigned32
         }

cCdmaClusterMemberAddressType OBJECT-TYPE
         SYNTAX      InetAddressType
         MAX-ACCESS  not-accessible
         STATUS      current
         DESCRIPTION
                 "This is IP address type of this PDSN cluster
                  member, which is used as index (combine with
                  cCdmaClusterMemberAddress) to identify a unique
                  cluster member entry."
         ::= { cCdmaClusterMemberEntry 1 }

cCdmaClusterMemberAddress OBJECT-TYPE
         SYNTAX      InetAddress
         MAX-ACCESS  not-accessible
         STATUS      current
         DESCRIPTION
                 "This is IP address of this PDSN cluster member,
                  which is used as index (combine with
                  cCdmaClusterMemberAddressType) to identify a unique
                  cluster member entry."
         ::= { cCdmaClusterMemberEntry 2 }

cCdmaClusterMemberStatus OBJECT-TYPE
         SYNTAX      INTEGER {
                        unknown(1),
                        ready(2),
                        adminProhibit(3)
                     }
         MAX-ACCESS  read-only
         STATUS      current
         DESCRIPTION
                 "The operational status of this PDSN:
                    - 'unknown' indicates cluster controller doesn't
                      know this member's status.
                    - 'ready' indicates this member is ready to serve 
                      call setup request.
                    - 'adminProhibit' indicates this member will not
                      new call setup request, but will maintain 
                      existing calls."
         ::= { cCdmaClusterMemberEntry 3 }

cCdmaClusterMemberLoad OBJECT-TYPE
         SYNTAX    Unsigned32
         UNITS "1%"
         MAX-ACCESS  read-only
         STATUS      current
         DESCRIPTION
                 "PDSN cluster member load as an aggregate percentage of
                  the maximum load that can be serviced."
         ::= { cCdmaClusterMemberEntry 4 }

-- ************************************************************************
-- PDSN notification variables
-- ************************************************************************

cCdmaNotifSeverityLevel OBJECT-TYPE
         SYNTAX      CCdmaServiceAffectedLevel 
         MAX-ACCESS  read-write
         STATUS      current
         DESCRIPTION
                 "This is the configured service affected level. Agent
                  generates notifications only if such notifications'
                  service affected level is higher than this value."
         DEFVAL      { major }
         ::= { cCdmaNotifConfig 1 }

-- *******************************************************************
-- Notification Objects: variables defined this group will be used by 
--                       notification only
-- *******************************************************************
cCdmaServiceAffectedLevel  OBJECT-TYPE
         SYNTAX      CCdmaServiceAffectedLevel
         MAX-ACCESS  read-only
         STATUS      current
         DESCRIPTION
                 "This is the severity level of affected service by 
                  this event/condition that causes this notification."
         ::= { cCdmaNotifObjects 1 }

cCdmaAffectedAddressType OBJECT-TYPE
         SYNTAX      InetAddressType
         MAX-ACCESS  read-only
         STATUS      deprecated
         DESCRIPTION
                 "This is the IP address type of affected device that 
                  generates this notification."
         ::= { cCdmaNotifObjects 2 }

cCdmaAffectedAddress OBJECT-TYPE
         SYNTAX      InetAddress
         MAX-ACCESS  read-only
         STATUS      deprecated
         DESCRIPTION
                 "This is the IP address of affected device that 
                  generates this notification."
         ::= { cCdmaNotifObjects 3 }

cCdmaAffectedMemberStatus  OBJECT-TYPE
         SYNTAX      INTEGER {
                        ready(1),
                        adminProhibit(2)
                     }
         MAX-ACCESS  read-only
         STATUS      deprecated
         DESCRIPTION
                 "The operational status of affected member PDSN."
         ::= { cCdmaNotifObjects 4 }

cCdmaAffectedCtrlStatus OBJECT-TYPE
         SYNTAX      INTEGER {
                        configured(1),
                        alive(2)
                     }
         MAX-ACCESS  read-only
         STATUS      deprecated
         DESCRIPTION
                 "The operational status of the affected cluster
                  controller."
         ::= { cCdmaNotifObjects 5 }

-- ******************************************************************
-- Notification definitions
-- ******************************************************************

cCdmaPdsnMIBNotifPrefix  OBJECT IDENTIFIER ::= { ciscoCdmaPdsnMIB 2 }
cCdmaPdsnMIBNotifs       OBJECT IDENTIFIER ::= { cCdmaPdsnMIBNotifPrefix 0 }
  
cCdmaSessionMaxAllowedNotif  NOTIFICATION-TYPE
           OBJECTS {
                    cCdmaSessionMaxAllowed
                   }
           STATUS current
           DESCRIPTION
                   "This notification indicates PDSN has reached the
                    maximum number of sessions the system can handle.
                    In this state new session request will be rejected.

                    Service affected level: critical"
           ::= { cCdmaPdsnMIBNotifs 1 }
  
cCdmaPcfMaxAllowedNotif  NOTIFICATION-TYPE
           OBJECTS {
                    cCdmaPcfMaxAllowed
                   }
           STATUS current
           DESCRIPTION
                   "This notification indicates PDSN has reached the 
                    maximum number of allowed PCF. In this state
                    request from new PCF will be rejected.

                    Service affected level: critical"
           ::= { cCdmaPdsnMIBNotifs 2 }
  
cCdmaSessionFormatErrorNotif  NOTIFICATION-TYPE
           OBJECTS {
                    cCdmaFailSessionMsid,
                    cCdmaFailSessionA11HaIp,
                    cCdmaFailSessionA11FaIp,
                    cCdmaFailSessionConnId
                   }
           STATUS obsolete
           DESCRIPTION
                   "This notification indicates PDSN received 
                      invalid
                    arguments from PCF leading to session termination.
                    The agent should not generate more than 1 trap 
                      of this
                    type per second to minimize the level of 
                      management
                    traffic on the network"
           ::= { cCdmaPdsnMIBNotifs 3 }
  
cCdmaSessionRegReqFailedNotif NOTIFICATION-TYPE
           OBJECTS {
                    cCdmaFailSessionMsid,
                    cCdmaFailSessionA11HaIp,
                    cCdmaFailSessionA11FaIp,
                    cCdmaFailSessionConnId,
                    cCdmaFailHistFailType
                   }
           STATUS current
           DESCRIPTION
                   "This notification indicates a Registration 
                    Request received has failed which may be due to
                    one of the following reasons:
                        insufficient resource, 
                        Administrative prohibition,
                        MN authentication failure,
                        registration id mismatch,
                        bad request,
                        unknown HA address 
                        or T  bit not set or unsupported VID.

                    The agent should not generate more than 1 trap 
                    of same type per second to minimize the level of
                    management traffic on the network.

                    Service affected level: minor"
           ::= { cCdmaPdsnMIBNotifs 4 }

cCdmaPdsnStatusChange NOTIFICATION-TYPE
           OBJECTS {
                    cCdmaServiceAffectedLevel,
                    cCdmaSystemStatus
                   }
           STATUS current
           DESCRIPTION
                   "This notification indicates status change of PDSN."
           ::= { cCdmaPdsnMIBNotifs 5 }

cCdmaSessionHighReached NOTIFICATION-TYPE
           OBJECTS {
                    cCdmaServiceAffectedLevel,
                    cCdmaSessionHighThreshold
                   }
           STATUS current
           DESCRIPTION
                   "This notification indicates a session high 
                    threshold has been has been reached."
           ::= { cCdmaPdsnMIBNotifs 6 }

cCdmaSessionLowReached NOTIFICATION-TYPE
           OBJECTS {
                    cCdmaServiceAffectedLevel,
                    cCdmaSessionHighThreshold
                   }
           STATUS deprecated
           DESCRIPTION
                   "This notification indicates a session low 
                    threshold has been has been reached."
           ::= { cCdmaPdsnMIBNotifs 7 }

cCdmaClusterSessionHighReached NOTIFICATION-TYPE
           OBJECTS {
                    cCdmaServiceAffectedLevel,
                    cCdmaClusterSessHighThreshold
                   }
           STATUS current
           DESCRIPTION
                   "This notification indicates a cluster session 
                    high threshold has been reached by PDSN cluster
                    controller."
           ::= { cCdmaPdsnMIBNotifs 8 }

cCdmaClusterSessionLowReached NOTIFICATION-TYPE
           OBJECTS {
                    cCdmaServiceAffectedLevel,
                    cCdmaClusterSessLowThreshold
                   }
           STATUS current
           DESCRIPTION
                   "This notification indicates a cluster session 
                    low threshold has been reached by PDSN cluster
                    controller.

                    Service affected level: Major/Warning"
           ::= { cCdmaPdsnMIBNotifs 9 }

cCdmaClusterMemberStatusChange NOTIFICATION-TYPE
           OBJECTS {
                    cCdmaServiceAffectedLevel,
                    cCdmaAffectedAddressType,
                    cCdmaAffectedAddress,
                    cCdmaAffectedMemberStatus
                   }
           STATUS deprecated
           DESCRIPTION
                   "Cluster controller detects member PDSN status
                    change"
           ::= { cCdmaPdsnMIBNotifs 10 }

cCdmaClusterCtrlStatusChange NOTIFICATION-TYPE
           OBJECTS {
                    cCdmaServiceAffectedLevel,
                    cCdmaAffectedAddressType,
                    cCdmaAffectedAddress,
                    cCdmaAffectedCtrlStatus
                   }
           STATUS deprecated
           DESCRIPTION
                   "Cluster member PDSN detects controller PDSN status
                    change"
           ::= { cCdmaPdsnMIBNotifs 11 }

cCdmaClusterMemberStatusChange2 NOTIFICATION-TYPE
           OBJECTS {
                    cCdmaClusterMemberStatus
                   }
           STATUS current
           DESCRIPTION
                   "Cluster controller detects member PDSN status
                    change"
           ::= { cCdmaPdsnMIBNotifs 12 }

cCdmaClusterCtrlStatusChange2 NOTIFICATION-TYPE
           OBJECTS {
                    cCdmaClusterCtrlStatus
                   }
           STATUS current
           DESCRIPTION
                   "Cluster member PDSN detects controller PDSN status
                    change"
           ::= { cCdmaPdsnMIBNotifs 13 }

cCdmaSessionLowReached2 NOTIFICATION-TYPE
           OBJECTS {
                    cCdmaServiceAffectedLevel,
                    cCdmaSessionLowThreshold
                   }
           STATUS current
           DESCRIPTION
                   "This notification indicates a session low 
                    threshold has been has been reached."
           ::= { cCdmaPdsnMIBNotifs 14 }

-- *************************************************************************
-- * RP Registration Request Errors
-- *************************************************************************

cCdmaRegReqInvPakLenErrs   OBJECT-TYPE
         SYNTAX      ZeroBasedCounter32
         MAX-ACCESS  read-only
         STATUS      current
         DESCRIPTION
                 "Invalid Registration request packet length while
                  parsing since system was last restarted" 
         ::= { cCdmaRPRegReqErrors 1 }

cCdmaRegReqInvProtocolErrs OBJECT-TYPE
         SYNTAX      ZeroBasedCounter32
         MAX-ACCESS  read-only
         STATUS      current
         DESCRIPTION
                 "Invalid Protocol value in the Registration Request 
                  Session Specific Extension since system was last
                  restarted" 
         ::= { cCdmaRPRegReqErrors 2 }

cCdmaRegReqInvFlagsErrs  OBJECT-TYPE
         SYNTAX      ZeroBasedCounter32
         MAX-ACCESS  read-only
         STATUS      current
         DESCRIPTION
                 "Invalid Flags value in the Registration Request 
                  since system was last restarted"
         ::= { cCdmaRPRegReqErrors 3 }

cCdmaRegReqInvMHAEKeyErrs OBJECT-TYPE
         SYNTAX      ZeroBasedCounter32
         MAX-ACCESS  read-only
         STATUS      current
         DESCRIPTION
                 "Invalid Authentication key in the Registration
                  Request Mobile-Home Authentication extension
                  since system was last restarted" 
         ::= { cCdmaRPRegReqErrors 4 }

cCdmaRegReqMismatchSPIErrs OBJECT-TYPE
         SYNTAX      ZeroBasedCounter32
         MAX-ACCESS  read-only
         STATUS      current
         DESCRIPTION
                 "Mismatch in SPI in the Registration Request 
                  Mobile-Home Authentication extension since system was 
                  last restarted"
         ::= { cCdmaRPRegReqErrors 5 }

cCdmaRegReqInvSPIErrs OBJECT-TYPE
         SYNTAX      ZeroBasedCounter32
         MAX-ACCESS  read-only
         STATUS      current
         DESCRIPTION
                 "Invalid SPI in the Registration Request 
                  Mobile-Home Authentication extension since system was 
                  last restarted"
         ::= { cCdmaRPRegReqErrors 6 }

cCdmaRegReqInvConnectionIDErrs OBJECT-TYPE
         SYNTAX      ZeroBasedCounter32
         MAX-ACCESS  read-only
         STATUS      current
         DESCRIPTION
                 "Invalid Connection ID in the Registration Request
                  since system was last restarted"
         ::= { cCdmaRPRegReqErrors 7 }

cCdmaRegReqInvMNIDErrs OBJECT-TYPE
         SYNTAX      ZeroBasedCounter32
         MAX-ACCESS  read-only
         STATUS      current
         DESCRIPTION
                 "Invalid MN ID in the Registration Request
                  since system was last restarted"
         ::= { cCdmaRPRegReqErrors 8 }

cCdmaRegReqInvMNIDTypeErrs OBJECT-TYPE
         SYNTAX      ZeroBasedCounter32
         MAX-ACCESS  read-only
         STATUS      current
         DESCRIPTION
                 "Invalid MN ID type in the Registration Request
                  since system was last restarted"
         ::= { cCdmaRPRegReqErrors 9 }

cCdmaRegReqInvMSIDLenErrs OBJECT-TYPE
         SYNTAX      ZeroBasedCounter32
         MAX-ACCESS  read-only
         STATUS      current
         DESCRIPTION
                 "Invalid MSID length in the Registration Request
                  since system was last restarted"
         ::= { cCdmaRPRegReqErrors 10 }

cCdmaRegReqMissingSSEErrs OBJECT-TYPE
         SYNTAX      ZeroBasedCounter32
         MAX-ACCESS  read-only
         STATUS      current
         DESCRIPTION
                 "Session Specific extension missing in the
                  Registration Request since system was last
                  restarted"
         ::= { cCdmaRPRegReqErrors 11 }

cCdmaRegReqMissingMHAEErrs OBJECT-TYPE
         SYNTAX      ZeroBasedCounter32
         MAX-ACCESS  read-only
         STATUS      current
         DESCRIPTION
                 "Mobile-Home Authentication extension missing in
                  the Registration Request since system was last
                  restarted"
         ::= { cCdmaRPRegReqErrors 12 }

cCdmaRegReqInvOrderErrs OBJECT-TYPE
         SYNTAX      ZeroBasedCounter32
         MAX-ACCESS  read-only
         STATUS      current
         DESCRIPTION
                 "Invalid order of the extensions in the Registration
                  Request since system was last restarted"
         ::= { cCdmaRPRegReqErrors 13 }

cCdmaRegReqInvVSEErrs OBJECT-TYPE
         SYNTAX      ZeroBasedCounter32
         MAX-ACCESS  read-only
         STATUS      current
         DESCRIPTION
                 "Invalid Vendor specific extensions in the Registration
                  Request since system was last restarted"
         ::= { cCdmaRPRegReqErrors 14 }

cCdmaRegReqInvAppTypeInVSEErrs OBJECT-TYPE
         SYNTAX      ZeroBasedCounter32
         MAX-ACCESS  read-only
         STATUS      current
         DESCRIPTION
                 "Invalid Application type in Vendor specific
                  extensions in  the Registration Request since system
                  was last restarted"
         ::= { cCdmaRPRegReqErrors 15 }

cCdmaRegReqDupAppTypeInVSEErrs OBJECT-TYPE
         SYNTAX      ZeroBasedCounter32
         MAX-ACCESS  read-only
         STATUS      current
         DESCRIPTION
                 "Duplicate Application type in Vendor specific
                  extensions in the Registration Request since system
                  was last restarted"
         ::= { cCdmaRPRegReqErrors 16 }

cCdmaRegReqInvAppSubTypeInVSEErrs OBJECT-TYPE
         SYNTAX      ZeroBasedCounter32
         MAX-ACCESS  read-only
         STATUS      current
         DESCRIPTION
                 "Invalid Sub Application type in Vendor specific
                  extensions in  the Registration Request since system
                  was last restarted"
         ::= { cCdmaRPRegReqErrors 17 }

cCdmaRegReqInvVendorIDInVSEErrs OBJECT-TYPE
         SYNTAX      ZeroBasedCounter32
         MAX-ACCESS  read-only
         STATUS      current
         DESCRIPTION
                 "Invalid Vendor ID in Vendor specific extensions in  
                  the Registration Request since system was last
                  restarted"
         ::= { cCdmaRPRegReqErrors 18 }

cCdmaRegReqDupCVSEErrs OBJECT-TYPE
         SYNTAX      ZeroBasedCounter32
         MAX-ACCESS  read-only
         STATUS      current
         DESCRIPTION
                 "Duplicate Critical Vendor extension in the
                  Registration Request since system was last
                  restarted"
         ::= { cCdmaRPRegReqErrors 19 }

cCdmaRegReqAcctUnknwnAttrErrs OBJECT-TYPE
         SYNTAX      ZeroBasedCounter32
         MAX-ACCESS  read-only
         STATUS      current
         DESCRIPTION
                 "Unknown Accounting attribute in the Registration
                  Request since system was last restarted"
         ::= { cCdmaRPRegReqErrors 20 }

cCdmaRegReqAcctInvLenAttrErrs OBJECT-TYPE
         SYNTAX      ZeroBasedCounter32
         MAX-ACCESS  read-only
         STATUS      current
         DESCRIPTION
                 "Invalid accounting attribute length in the
                  Registration Request since system was last
                  restarted"
         ::= { cCdmaRPRegReqErrors 21 }

cCdmaRegReqAcctDupAttrErrs OBJECT-TYPE
         SYNTAX      ZeroBasedCounter32
         MAX-ACCESS  read-only
         STATUS      current
         DESCRIPTION
                 "Duplicate accounting attribute received in the
                  Registration Request since system was last
                  restarted"
         ::= { cCdmaRPRegReqErrors 22 }

cCdmaRegReqAcctRecRetransErrs OBJECT-TYPE
         SYNTAX      ZeroBasedCounter32
         MAX-ACCESS  read-only
         STATUS      current
         DESCRIPTION
                 "Same accounting sequence number and record type in
                  the Registration Requests airlink record not
                  updated since system was last restarted"
         ::= { cCdmaRPRegReqErrors 23 }

cCdmaRegReqAcctInvSeqNumErrs OBJECT-TYPE
         SYNTAX      ZeroBasedCounter32
         MAX-ACCESS  read-only
         STATUS      current
         DESCRIPTION
                 "Invalid sequence number in the airlink accounting
                  record Registration Requests siliently discarded
                  since system was last restarted"
         ::= { cCdmaRPRegReqErrors 24 }

cCdmaRegReqDuplicateGREKeyErrs OBJECT-TYPE
         SYNTAX      ZeroBasedCounter32
         MAX-ACCESS  read-only
         STATUS      current
         DESCRIPTION
                 "Duplicate GRE Key received in the Registration Request
                  for different MSID from the same PCF since system was
                  last restarted"
         ::= { cCdmaRPRegReqErrors 25 }

cCdmaRegReqSameGREKeySetupRcvdErrs OBJECT-TYPE
         SYNTAX      ZeroBasedCounter32
         MAX-ACCESS  read-only
         STATUS      current
         DESCRIPTION
                 "Same GRE Key and Airlink setup received in the
                  Registration Request for existing session since
                  system was last restarted"
         ::= { cCdmaRPRegReqErrors 26 }

cCdmaRegReqGREKeyChngNoSetupErrs OBJECT-TYPE
         SYNTAX      ZeroBasedCounter32
         MAX-ACCESS  read-only
         STATUS      current
         DESCRIPTION
                 "GRE changed without airlink setup received in the
                  Registration Request for existing session since
                  system was last restarted"
         ::= { cCdmaRPRegReqErrors 27 }

cCdmaRegReqInitNoSetupErrs OBJECT-TYPE
         SYNTAX      ZeroBasedCounter32
         MAX-ACCESS  read-only
         STATUS      current
         DESCRIPTION
                 "Airlink Setup record not received in the Initial
                  Registration Request since system was last restarted"
         ::= { cCdmaRPRegReqErrors 28 }

cCdmaRegReqStartBeforeSetupErrs OBJECT-TYPE
         SYNTAX      ZeroBasedCounter32
         MAX-ACCESS  read-only
         STATUS      current
         DESCRIPTION
                 "Airlink Start record received before the Airlink setup
                  in the Registration Request since system was last
                  restarted"
         ::= { cCdmaRPRegReqErrors 29 }

cCdmaRegReqStartOnCloseErrs OBJECT-TYPE
         SYNTAX      ZeroBasedCounter32
         MAX-ACCESS  read-only
         STATUS      current
         DESCRIPTION
                 "Airlink Start record received in the De-Registration
                  Request since system was last restarted"
         ::= { cCdmaRPRegReqErrors 30 }

cCdmaRegReqStartOnActiveErrs OBJECT-TYPE
         SYNTAX      ZeroBasedCounter32
         MAX-ACCESS  read-only
         STATUS      current
         DESCRIPTION
                 "Airlink Start record received in the Registration 
                  Request for already active session since system was
                  last restarted"
         ::= { cCdmaRPRegReqErrors 31 }

cCdmaRegReqStopOnDormantErrs OBJECT-TYPE
         SYNTAX      ZeroBasedCounter32
         MAX-ACCESS  read-only
         STATUS      current
         DESCRIPTION
                 "Airlink Stop record received in the Registration 
                  Request for already dormant session since system
                  was last restarted"
         ::= { cCdmaRPRegReqErrors 32 }

cCdmaRegReqInitRcvdStopErrs OBJECT-TYPE
         SYNTAX      ZeroBasedCounter32
         MAX-ACCESS  read-only
         STATUS      current
         DESCRIPTION
                 "Airlink Stop record received in the Initial
                  Registration Request since system was last
                  restarted"
         ::= { cCdmaRPRegReqErrors 33 }

cCdmaRegReqInitRcvdSDBErrs OBJECT-TYPE
         SYNTAX      ZeroBasedCounter32
         MAX-ACCESS  read-only
         STATUS      current
         DESCRIPTION
                 "Airlink SDB received in the Initial Registration
                  Request since system was last restarted"
         ::= { cCdmaRPRegReqErrors 34 }

cCdmaRegReqInvAirlinkRecErrs OBJECT-TYPE
         SYNTAX      ZeroBasedCounter32
         MAX-ACCESS  read-only
         STATUS      current
         DESCRIPTION
                 "Invalid Accounting Airlink record type in the
                  Registration Request since system was last
                  restarted"
         ::= { cCdmaRPRegReqErrors 35 }

cCdmaRegReqDeRegNoSessionErrs OBJECT-TYPE
         SYNTAX      ZeroBasedCounter32
         MAX-ACCESS  read-only
         STATUS      current
         DESCRIPTION
                 "De-Registration Requests denied for non existing 
                  sessions since system was last restarted"
         ::= { cCdmaRPRegReqErrors 36 }

cCdmaRegReqReRegInDisconnectErrs OBJECT-TYPE
         SYNTAX      ZeroBasedCounter32
         MAX-ACCESS  read-only
         STATUS      current
         DESCRIPTION
                 "Re-Registration Request received for the session in
                  the disconnecting or deleting state, therefore the
                  registration request is discarded since system was
                  last restarted"
         ::= { cCdmaRPRegReqErrors 37 }

cCdmaRegReqMemFailErrs OBJECT-TYPE
         SYNTAX      ZeroBasedCounter32
         MAX-ACCESS  read-only
         STATUS      current
         DESCRIPTION
                 "Registration Request discarded due to memory
                  allocation failure during processing since
                  system was last restarted"
         ::= { cCdmaRPRegReqErrors 38 }

cCdmaRpRegReqMaxSessionReachedErrs OBJECT-TYPE
         SYNTAX      ZeroBasedCounter32
         MAX-ACCESS  read-only
         STATUS      current
         DESCRIPTION
                 "Registration request rejected because of maximum
                  limit or configured number of session reached since
                  system was last restarted"
         ::= { cCdmaRPRegReqErrors 39 }

-- *************************************************************************
-- * RP Registration Update Ack Errors
-- *************************************************************************

cCdmaRegUpdAckInvPakLenErrs   OBJECT-TYPE
         SYNTAX      ZeroBasedCounter32
         MAX-ACCESS  read-only
         STATUS      current
         DESCRIPTION
                 "Invalid Registration Update Ack packet length while
                  parsing since system was last restarted" 
         ::= { cCdmaRPRegUpdAckErrors 1 }

cCdmaRegUpdAckInvProtocolErrs OBJECT-TYPE
         SYNTAX      ZeroBasedCounter32
         MAX-ACCESS  read-only
         STATUS      current
         DESCRIPTION
                 "Invalid Protocol value in the Registration Update Ack 
                  Session Specific Extension since system was last
                  restarted" 
         ::= { cCdmaRPRegUpdAckErrors 2 }

cCdmaRegUpdAckInvRUAEKeyErrs OBJECT-TYPE
         SYNTAX      ZeroBasedCounter32
         MAX-ACCESS  read-only
         STATUS      current
         DESCRIPTION
                 "Invalid Authentication key in the Registration Update
                  Ack Registration Update Authentication extension
                  since system was last restarted" 
         ::= { cCdmaRPRegUpdAckErrors 3 }

cCdmaRegUpdAckInvSPIErrs OBJECT-TYPE
         SYNTAX      ZeroBasedCounter32
         MAX-ACCESS  read-only
         STATUS      current
         DESCRIPTION
                 "Invalid SPI in the Registration Update Ack 
                  Registration Update Authentication extension 
                  since system was  last restarted"
         ::= { cCdmaRPRegUpdAckErrors 4 }

cCdmaRegUpdAckInvConnectionIDErrs OBJECT-TYPE
         SYNTAX      ZeroBasedCounter32
         MAX-ACCESS  read-only
         STATUS      current
         DESCRIPTION
                 "Invalid Connection ID in the Registration Update Ack
                  since system was last restarted"
         ::= { cCdmaRPRegUpdAckErrors 5 }

cCdmaRegUpdAckInvMNIDErrs OBJECT-TYPE
         SYNTAX      ZeroBasedCounter32
         MAX-ACCESS  read-only
         STATUS      current
         DESCRIPTION
                 "Invalid MN ID in the Registration Update Ack
                  since system was last restarted"
         ::= { cCdmaRPRegUpdAckErrors 6 }

cCdmaRegUpdAckInvMNIDTypeErrs OBJECT-TYPE
         SYNTAX      ZeroBasedCounter32
         MAX-ACCESS  read-only
         STATUS      current
         DESCRIPTION
                 "Invalid MN ID type in the Registration Update Ack
                  since system was last restarted"
         ::= { cCdmaRPRegUpdAckErrors 7 }

cCdmaRegUpdAckInvMSIDLenErrs OBJECT-TYPE
         SYNTAX      ZeroBasedCounter32
         MAX-ACCESS  read-only
         STATUS      current
         DESCRIPTION
                 "Invalid MSID length in the Registration Update Ack
                  since system was last restarted"
         ::= { cCdmaRPRegUpdAckErrors 8 }

cCdmaRegUpdAckMissingSSEErrs OBJECT-TYPE
         SYNTAX      ZeroBasedCounter32
         MAX-ACCESS  read-only
         STATUS      current
         DESCRIPTION
                 "Session Specific extension missing in the
                  Registration Update Ack since system was last
                  restarted"
         ::= { cCdmaRPRegUpdAckErrors 9 }

cCdmaRegUpdAckMissingRUAEErrs OBJECT-TYPE
         SYNTAX      ZeroBasedCounter32
         MAX-ACCESS  read-only
         STATUS      current
         DESCRIPTION
                 "Registration Update Authentication extension missing
                  in the Registration Update Ack since system was last
                  restarted"
         ::= { cCdmaRPRegUpdAckErrors 10 }

cCdmaRegUpdAckInvOrderErrs OBJECT-TYPE
         SYNTAX      ZeroBasedCounter32
         MAX-ACCESS  read-only
         STATUS      current
         DESCRIPTION
                 "Invalid order of the extensions in the Registration
                  Update Ack since system was last restarted"
         ::= { cCdmaRPRegUpdAckErrors 11 }

cCdmaRegUpdAckInvVSEErrs OBJECT-TYPE
         SYNTAX      ZeroBasedCounter32
         MAX-ACCESS  read-only
         STATUS      current
         DESCRIPTION
                 "Invalid Vendor specific extensions in the
                  Registration Update Ack since system was last
                  restarted"
         ::= { cCdmaRPRegUpdAckErrors 12 }

cCdmaRegUpdAckNoSessionErrs OBJECT-TYPE
         SYNTAX      ZeroBasedCounter32
         MAX-ACCESS  read-only
         STATUS      current
         DESCRIPTION
                 "Registration Update Ack is discarded since system
                  was last restarted"
         ::= { cCdmaRPRegUpdAckErrors 13 }

cCdmaRegUpdAckMemFailErrs OBJECT-TYPE
         SYNTAX      ZeroBasedCounter32
         MAX-ACCESS  read-only
         STATUS      current
         DESCRIPTION
                 "Registration Update Ack discarded due to memory
                  allocation failure during processing since system
                  was last restarted"
         ::= { cCdmaRPRegUpdAckErrors 14 }

-- *************************************************************************
-- * RP Session Update Ack Errors
-- *************************************************************************

cCdmaSessUpdAckInvPakLenErrs   OBJECT-TYPE
         SYNTAX      ZeroBasedCounter32
         MAX-ACCESS  read-only
         STATUS      current
         DESCRIPTION
                 "Invalid Session Update Ack packet length while
                  parsing since system was last restarted" 
         ::= { cCdmaRPSessUpdAckErrors 1 }

cCdmaSessUpdAckInvProtocolErrs OBJECT-TYPE
         SYNTAX      ZeroBasedCounter32
         MAX-ACCESS  read-only
         STATUS      current
         DESCRIPTION
                 "Invalid Protocol value in the Session Update Ack 
                  Session Specific Extension since system was last
                  restarted" 
         ::= { cCdmaRPSessUpdAckErrors 2 }

cCdmaSessUpdAckInvRUAEKeyErrs OBJECT-TYPE
         SYNTAX      ZeroBasedCounter32
         MAX-ACCESS  read-only
         STATUS      current
         DESCRIPTION
                 "Invalid Authentication key in the Session Update Ack 
                  Registration Update Authentication extension since
                  system was last restarted" 
         ::= { cCdmaRPSessUpdAckErrors 3 }

cCdmaSessUpdAckInvSPIErrs OBJECT-TYPE
         SYNTAX      ZeroBasedCounter32
         MAX-ACCESS  read-only
         STATUS      current
         DESCRIPTION
                 "Invalid SPI in the Session Update Ack 
                  Session Update Authentication extension 
                  since system was  last restarted"
         ::= { cCdmaRPSessUpdAckErrors 4 }

cCdmaSessUpdAckInvConnectionIDErrs OBJECT-TYPE
         SYNTAX      ZeroBasedCounter32
         MAX-ACCESS  read-only
         STATUS      current
         DESCRIPTION
                 "Invalid Connection ID in the Session Update Ack
                  since system was last restarted"
         ::= { cCdmaRPSessUpdAckErrors 5 }

cCdmaSessUpdAckInvMNIDErrs OBJECT-TYPE
         SYNTAX      ZeroBasedCounter32
         MAX-ACCESS  read-only
         STATUS      current
         DESCRIPTION
                 "Invalid MN ID in the Session Update Ack
                  since system was last restarted"
         ::= { cCdmaRPSessUpdAckErrors 6 }

cCdmaSessUpdAckInvMNIDTypeErrs OBJECT-TYPE
         SYNTAX      ZeroBasedCounter32
         MAX-ACCESS  read-only
         STATUS      current
         DESCRIPTION
                 "Invalid MN ID type in the Session Update Ack
                  since system was last restarted"
         ::= { cCdmaRPSessUpdAckErrors 7 }

cCdmaSessUpdAckInvMSIDLenErrs OBJECT-TYPE
         SYNTAX      ZeroBasedCounter32
         MAX-ACCESS  read-only
         STATUS      current
         DESCRIPTION
                 "Invalid MSID length in the Session Update Ack
                  since system was last restarted"
         ::= { cCdmaRPSessUpdAckErrors 8 }

cCdmaSessUpdAckMissingSSEErrs OBJECT-TYPE
         SYNTAX      ZeroBasedCounter32
         MAX-ACCESS  read-only
         STATUS      current
         DESCRIPTION
                 "Session Specific extension missing in the Session 
                  Update Ack since system was last restarted"
         ::= { cCdmaRPSessUpdAckErrors 9 }

cCdmaSessUpdAckMissingRUAEErrs OBJECT-TYPE
         SYNTAX      ZeroBasedCounter32
         MAX-ACCESS  read-only
         STATUS      current
         DESCRIPTION
                 "Session Update Authentication extension missing in
                  the Session Update Ack since system was last
                  restarted"
         ::= { cCdmaRPSessUpdAckErrors 10 }

cCdmaSessUpdAckInvOrderErrs OBJECT-TYPE
         SYNTAX      ZeroBasedCounter32
         MAX-ACCESS  read-only
         STATUS      current
         DESCRIPTION
                 "Invalid order of the extensions in the Session
                  Update Ack since system was last restarted"
         ::= { cCdmaRPSessUpdAckErrors 11 }

cCdmaSessUpdAckInvVSEErrs OBJECT-TYPE
         SYNTAX      ZeroBasedCounter32
         MAX-ACCESS  read-only
         STATUS      current
         DESCRIPTION
                 "Invalid Vendor specific extensions in the Session
                  Update Ack since system was last restarted"
         ::= { cCdmaRPSessUpdAckErrors 12 }

cCdmaSessUpdAckNoSessionErrs OBJECT-TYPE
         SYNTAX      ZeroBasedCounter32
         MAX-ACCESS  read-only
         STATUS      current
         DESCRIPTION
                 "Session Update Ack is discarded since system 
                  was last restarted"
         ::= { cCdmaRPSessUpdAckErrors 13 }

cCdmaSessUpdAckMemFailErrs OBJECT-TYPE
         SYNTAX      ZeroBasedCounter32
         MAX-ACCESS  read-only
         STATUS      current
         DESCRIPTION
                 "Session Update Ack discarded due to memory allocation
                  failure during processing since system was last
                  restarted"
         ::= { cCdmaRPSessUpdAckErrors 14 }

-- *************************************************************************
-- * RP Registration Reply Errors
-- *************************************************************************

cCdmaRegRplyInternalErrs OBJECT-TYPE
         SYNTAX      ZeroBasedCounter32
         MAX-ACCESS  read-only
         STATUS      current
         DESCRIPTION
                 "Registration reply not sent due to internal error
                  during processing since system was last restarted"
         ::= { cCdmaRPRegReplyErrors 1 }

cCdmaRegRplyMemFailErrs OBJECT-TYPE
         SYNTAX      ZeroBasedCounter32
         MAX-ACCESS  read-only
         STATUS      current
         DESCRIPTION
                 "Registration reply not sent due to memory allocation
                  failure during processing since system was last
                  restarted"
         ::= { cCdmaRPRegReplyErrors 2 }

cCdmaRpRplyPCFNoSecOrParseErrs OBJECT-TYPE
         SYNTAX      ZeroBasedCounter32
         MAX-ACCESS  read-only
         STATUS      current
         DESCRIPTION
                 "Cannot send Reply to PCF because security association
                  not found for the PCF or Parse error of Request since 
                  system was last restarted"
         ::= {cCdmaRPRegReplyErrors 3 }

-- *************************************************************************
-- * RP Registration Update Errors
-- *************************************************************************

cCdmaRegUpdInternalErrs OBJECT-TYPE
         SYNTAX      ZeroBasedCounter32
         MAX-ACCESS  read-only
         STATUS      current
         DESCRIPTION
                 "Registration update not sent due to internal error
                  during processing since system was last restarted"
         ::= { cCdmaRPRegUpdErrors 1 }

cCdmaRegUpdMemFailErrs OBJECT-TYPE
         SYNTAX      ZeroBasedCounter32
         MAX-ACCESS  read-only
         STATUS      current
         DESCRIPTION
                 "Registration update not sent due to memory allocation
                  failure during processing since system was last
                  restarted"
         ::= { cCdmaRPRegUpdErrors 2 }

-- *************************************************************************
-- * RP Session Update Errors
-- *************************************************************************

cCdmaSessUpdInternalErrs OBJECT-TYPE
         SYNTAX      ZeroBasedCounter32
         MAX-ACCESS  read-only
         STATUS      current
         DESCRIPTION
                 "Session update not sent due to internal error
                  during processing since system was last restarted"
         ::= { cCdmaRPSessUpdErrors 1 }

cCdmaSessUpdMemFailErrs OBJECT-TYPE
         SYNTAX      ZeroBasedCounter32
         MAX-ACCESS  read-only
         STATUS      current
         DESCRIPTION
                 "Session update not sent due to memory allocation
                  failure during processing since system was last
                  restarted"
         ::= { cCdmaRPSessUpdErrors 2 }

-- *************************************************************************
-- * Conformance
-- *************************************************************************

cCdmaPdsnMIBConformance  OBJECT IDENTIFIER ::= { ciscoCdmaPdsnMIB 3 }
cCdmaPdsnMIBCompliances  OBJECT IDENTIFIER ::= { cCdmaPdsnMIBConformance 1 }
cCdmaPdsnMIBGroups       OBJECT IDENTIFIER ::= { cCdmaPdsnMIBConformance 2 }


-- *************************************************************************
-- * Compliance
-- *************************************************************************

cCdmaPdsnMIBCompliance MODULE-COMPLIANCE
         STATUS obsolete
         DESCRIPTION
                 "The compliance statement for entities which implement
                 the CDMA PDSN Management MIB."
         MODULE  -- this module
         MANDATORY-GROUPS {
                     cCdmaSystemPdsnGroup,
                     cCdmaNotifPdsnGroup
         }
                 
         OBJECT      cCdmaPcfMaxAllowed
         MIN-ACCESS  read-only
         DESCRIPTION
                 "Write access is not required"

         OBJECT      cCdmaSessionPdsnAuthenTimer
         MIN-ACCESS  read-only
         DESCRIPTION
                 "Write access is not required"

         OBJECT      cCdmaSessionPdsnMaxFailHistory
         MIN-ACCESS  read-only
         DESCRIPTION
                 "Write access is not required"

         OBJECT      cCdmaSessionMaxNotifEnabled
         MIN-ACCESS  read-only
         DESCRIPTION
                 "Write access is not required"

         OBJECT      cCdmaPcfMaxAllowedNotifEnabled
         MIN-ACCESS  read-only
         DESCRIPTION
                 "Write access is not required"

         ::= { cCdmaPdsnMIBCompliances 1 }

cCdmaPdsnMIBComplianceRev1 MODULE-COMPLIANCE
         STATUS obsolete
         DESCRIPTION
                 "The compliance statement for entities which implement
                 the CDMA PDSN Management MIB."
         MODULE  -- this module
         MANDATORY-GROUPS {
                     cCdmaSystemPdsnGroupRev1,
                     cCdmaNotifPdsnGroupRev1
         }

         OBJECT      cCdmaPcfMaxAllowed
         MIN-ACCESS  read-only
         DESCRIPTION
                 "Write access is not required"

         OBJECT      cCdmaSessionPdsnAuthenTimer
         MIN-ACCESS  read-only
         DESCRIPTION
                 "Write access is not required"

         OBJECT      cCdmaSessionPdsnMaxFailHistory
         MIN-ACCESS  read-only
         DESCRIPTION
                 "Write access is not required"

         OBJECT      cCdmaSessionMaxNotifEnabled
         MIN-ACCESS  read-only
         DESCRIPTION
                 "Write access is not required"

         OBJECT      cCdmaPcfMaxAllowedNotifEnabled
         MIN-ACCESS  read-only
         DESCRIPTION
                 "Write access is not required"

         ::= { cCdmaPdsnMIBCompliances 2 }

cCdmaPdsnMIBComplianceRev2 MODULE-COMPLIANCE
         STATUS obsolete  -- superseded by cCdmaPdsnMIBComplianceRev3
         DESCRIPTION
                 "The compliance statement for entities which implement
                 the CDMA PDSN Management MIB."
         MODULE  -- this module
         MANDATORY-GROUPS {
                     cCdmaSystemPdsnGroupRev2,
                     cCdmaNotifPdsnGroupRev1
         }

         OBJECT      cCdmaPcfMaxAllowed
         MIN-ACCESS  read-only
         DESCRIPTION
                 "Write access is not required"

         OBJECT      cCdmaSessionPdsnAuthenTimer
         MIN-ACCESS  read-only
         DESCRIPTION
                 "Write access is not required"

         OBJECT      cCdmaSessionPdsnMaxFailHistory
         MIN-ACCESS  read-only
         DESCRIPTION
                 "Write access is not required"

         OBJECT      cCdmaSessionMaxNotifEnabled
         MIN-ACCESS  read-only
         DESCRIPTION
                 "Write access is not required"

         OBJECT      cCdmaPcfMaxAllowedNotifEnabled
         MIN-ACCESS  read-only
         DESCRIPTION
                 "Write access is not required"

         ::= { cCdmaPdsnMIBCompliances 3 }

cCdmaPdsnMIBComplianceRev3 MODULE-COMPLIANCE
         STATUS deprecated -- superseded by cCdmaPdsnMIBComplianceRev4
         DESCRIPTION
                 "The compliance statement for entities which implement
                 the CDMA PDSN Management MIB for R1.2."
         MODULE  -- this module
         MANDATORY-GROUPS {
                     cCdmaSystemPdsnGroupRev3,
                     cCdmaNotifPdsnGroupRev2
         }
         OBJECT      cCdmaPcfMaxAllowed
         MIN-ACCESS  read-only
         DESCRIPTION
                 "Write access is not required"

         OBJECT      cCdmaSessionPdsnMaxFailHistory
         MIN-ACCESS  read-only
         DESCRIPTION
                 "Write access is not required"

         OBJECT      cCdmaSessionMaxNotifEnabled
         MIN-ACCESS  read-only
         DESCRIPTION
                 "Write access is not required"

         OBJECT      cCdmaPcfMaxAllowedNotifEnabled
         MIN-ACCESS  read-only
         DESCRIPTION
                 "Write access is not required"

         OBJECT      cCdmaSessionHighThreshold
         MIN-ACCESS  read-only
         DESCRIPTION
                 "Write access is not required"

         OBJECT      cCdmaSessionLowThreshold
         MIN-ACCESS  read-only
         DESCRIPTION
                 "Write access is not required"

         OBJECT      cCdmaNotifSeverityLevel
         MIN-ACCESS  read-only
         DESCRIPTION
                 "Write access is not required"

         ::= { cCdmaPdsnMIBCompliances 4 }

cCdmaPdsnMIBComplianceRev4 MODULE-COMPLIANCE
         STATUS deprecated -- superseded by cCdmaPdsnMIBComplianceRev5
         DESCRIPTION
                 "The compliance statement for entities which implement
                 the CDMA PDSN Management MIB for R1.2."
         MODULE  -- this module
         MANDATORY-GROUPS {
                     cCdmaSystemPdsnGroupRev4,
                     cCdmaNotifPdsnGroupRev2
         }
         OBJECT      cCdmaPcfMaxAllowed
         MIN-ACCESS  read-only
         DESCRIPTION
                 "Write access is not required"

         OBJECT      cCdmaSessionPdsnMaxFailHistory
         MIN-ACCESS  read-only
         DESCRIPTION
                 "Write access is not required"

         OBJECT      cCdmaSessionMaxNotifEnabled
         MIN-ACCESS  read-only
         DESCRIPTION
                 "Write access is not required"

         OBJECT      cCdmaPcfMaxAllowedNotifEnabled
         MIN-ACCESS  read-only
         DESCRIPTION
                 "Write access is not required"

         OBJECT      cCdmaSessionHighThreshold
         MIN-ACCESS  read-only
         DESCRIPTION
                 "Write access is not required"

         OBJECT      cCdmaSessionLowThreshold
         MIN-ACCESS  read-only
         DESCRIPTION
                 "Write access is not required"

         OBJECT      cCdmaNotifSeverityLevel
         MIN-ACCESS  read-only
         DESCRIPTION
                 "Write access is not required"

         ::= { cCdmaPdsnMIBCompliances 5 }        
         
cCdmaPdsnMIBComplianceRev5 MODULE-COMPLIANCE
         STATUS deprecated -- superseded by cCdmaPdsnMIBComplianceRev6
         DESCRIPTION
                 "The compliance statement for entities which implement
                 the CDMA PDSN Management MIB for R2.0"
         MODULE  -- this module
         MANDATORY-GROUPS {
                     cCdmaSystemPdsnGroupRev5,
                     cCdmaNotifPdsnGroupRev3,
                     cCdmaPdsnPcfSoRpRegGroup,
                     cCdmaPdsnPcfSoPppGroup
         }
         OBJECT      cCdmaPcfMaxAllowed
         MIN-ACCESS  read-only
         DESCRIPTION
                 "Write access is not required"

         OBJECT      cCdmaSessionPdsnMaxFailHistory
         MIN-ACCESS  read-only
         DESCRIPTION
                 "Write access is not required"

         OBJECT      cCdmaSessionMaxNotifEnabled
         MIN-ACCESS  read-only
         DESCRIPTION
                 "Write access is not required"

         OBJECT      cCdmaPcfMaxAllowedNotifEnabled
         MIN-ACCESS  read-only
         DESCRIPTION
                 "Write access is not required"

         OBJECT      cCdmaSessionHighThreshold
         MIN-ACCESS  read-only
         DESCRIPTION
                 "Write access is not required"

         OBJECT      cCdmaSessionLowThreshold
         MIN-ACCESS  read-only
         DESCRIPTION
                 "Write access is not required"

         OBJECT      cCdmaNotifSeverityLevel
         MIN-ACCESS  read-only
         DESCRIPTION
                 "Write access is not required"

         ::= { cCdmaPdsnMIBCompliances 6 }

cCdmaPdsnMIBComplianceRev6 MODULE-COMPLIANCE
         STATUS current
         DESCRIPTION
                 "The compliance statement for entities which implement
                 the CDMA PDSN Management MIB for R3.0"
         MODULE  -- this module
         MANDATORY-GROUPS {
                     cCdmaSystemPdsnGroupRev5,
                     cCdmaNotifPdsnGroupRev3,
                     cCdmaPdsnPcfSoRpRegGroup,
                     cCdmaPdsnPcfSoPppGroup,
                     cCdmaSystemPdsnGroupSup1,
                     cCdmaPdsnPcfSoRpRegGroupSup1
         }
         OBJECT      cCdmaPcfMaxAllowed
         MIN-ACCESS  read-only
         DESCRIPTION
                 "Write access is not required"

         OBJECT      cCdmaSessionPdsnMaxFailHistory
         MIN-ACCESS  read-only
         DESCRIPTION
                 "Write access is not required"

         OBJECT      cCdmaSessionMaxNotifEnabled
         MIN-ACCESS  read-only
         DESCRIPTION
                 "Write access is not required"

         OBJECT      cCdmaPcfMaxAllowedNotifEnabled
         MIN-ACCESS  read-only
         DESCRIPTION
                 "Write access is not required"

         OBJECT      cCdmaSessionHighThreshold
         MIN-ACCESS  read-only
         DESCRIPTION
                 "Write access is not required"

         OBJECT      cCdmaSessionLowThreshold
         MIN-ACCESS  read-only
         DESCRIPTION
                 "Write access is not required"

         OBJECT      cCdmaNotifSeverityLevel
         MIN-ACCESS  read-only
         DESCRIPTION
                 "Write access is not required"

         ::= { cCdmaPdsnMIBCompliances 7 }
         
-- *************************************************************************
-- * Units of Conformance
-- *************************************************************************

cCdmaSystemPdsnGroup OBJECT-GROUP
         OBJECTS {
             cCdmaSessionTotal,
             cCdmaSessionMaxAllowed,
             cCdmaPcfTotal,
             cCdmaPcfMaxAllowed,
             cCdmaSimpleIpFlowTotal,
             cCdmaMobileIpFlowTotal,
             cCdmaProxyMobileIpFlowTotal,
             cCdmaSessionFailTotal,
             cCdmaServingPdsnHostname,
             cCdmaSessionPdsnAuthenTimer,
             cCdmaSessionPdsnMaxFailHistory,
             cCdmaSessionMaxNotifEnabled,
             cCdmaPcfMaxAllowedNotifEnabled,
             cCdmaFormatErrorNotifEnabled,

             cCdmaPcfSessionTotal,
             cCdmaPcfSessionMaxTotal,
             cCdmaPcfErrorTotal,

             cCdmaSessionMsidType,
             cCdmaSessionConnId,
             cCdmaSessionEsn,
             cCdmaSessionPdsnIp,
             cCdmaSessionFaIp,
             cCdmaSessionA11HaIp,
             cCdmaSessionA11FaIp,
             cCdmaSessionKey,
             cCdmaSessionMoMtInd,
             cCdmaActiveConnTime,
             cCdmaSessionPppCompressEnabled,
             cCdmaSessionVJCompressEnabled,
             cCdmaSessionServiceOption,
             cCdmaSessionConnStartTime,
             cCdmaSessionFlowCount,

             cCdmaSessionNai,
             cCdmaSessionHaIpAddress,
             cCdmaSessionFlowTechnology,
             cCdmaSessionAddressingScheme,
             cCdmaSessionTunnelProt,

             cCdmaFailSessionMsid,
             cCdmaFailSessionMsidType,
             cCdmaFailSessionEsn,
             cCdmaFailSessionA11HaIp,
             cCdmaFailSessionA11FaIp,
             cCdmaFailSessionConnId,
             cCdmaFailSessionKey,
             cCdmaFailHistFailTime,
             cCdmaFailHistFailType
        }
         STATUS obsolete
         DESCRIPTION
                 "A collection of objects needed for PDSN network management."
         ::= { cCdmaPdsnMIBGroups 1 }

  cCdmaNotifPdsnGroup  NOTIFICATION-GROUP
           NOTIFICATIONS
           {
             cCdmaSessionMaxAllowedNotif,
             cCdmaPcfMaxAllowedNotif,
             cCdmaSessionFormatErrorNotif
           }
           STATUS      obsolete
           DESCRIPTION
                   "The notifications related to PDSN network 
                    management."
           ::= { cCdmaPdsnMIBGroups 2 }

  cCdmaSystemPdsnGroupRev1 OBJECT-GROUP
         OBJECTS {
             cCdmaSessionTotal,
             cCdmaSessionMaxAllowed,
             cCdmaPcfTotal,
             cCdmaPcfMaxAllowed,
             cCdmaSimpleIpFlowTotal,
             cCdmaMobileIpFlowTotal,
             cCdmaProxyMobileIpFlowTotal,
             cCdmaSessionFailTotal,
             cCdmaServingPdsnHostname,
             cCdmaSessionPdsnAuthenTimer,
             cCdmaSessionPdsnMaxFailHistory,
             cCdmaSessionMaxNotifEnabled,
             cCdmaPcfMaxAllowedNotifEnabled,
             cCdmaRegReqFailedNotifEnabled,

             cCdmaPcfSessionTotal,
             cCdmaPcfErrorTotal,

             cCdmaSessionMsidType,
             cCdmaSessionEsn,
             cCdmaSessionPdsnIp,
             cCdmaSessionFaIp,
             cCdmaSessionA11HaIp,
             cCdmaSessionA11FaIp,
             cCdmaSessionKey,
             cCdmaSessionConnId,
             cCdmaSessionPppCompressEnabled,
             cCdmaSessionVJCompressEnabled,
             cCdmaSessionServiceOption,
             cCdmaSessionSentOctets,
             cCdmaSessionRcvdOctets,
             cCdmaSessionSentPkts,
             cCdmaSessionRcvdPkts,
             cCdmaSessionDiscardedOutPkts,
             cCdmaSessionDiscardedInPkts,
             cCdmaSessionConnStartTime,
             cCdmaActiveConnTime,
             cCdmaSessionFlowCount,
             cCdmaSessionStatus,
             cCdmaSessionRegLifeTime,
             cCdmaSessionRegTimeToExpire,
             cCdmaSessionGREFromIPPkts,
             cCdmaSessionGREToIPPkts,

             cCdmaSessionNai,
             cCdmaSessionHaIpAddress,
             cCdmaSessionFlowTechnology,
             cCdmaSessionAddressingScheme,
             cCdmaSessionTunnelProt,            

             cCdmaFailSessionMsid,
             cCdmaFailSessionMsidType,
             cCdmaFailSessionEsn,
             cCdmaFailSessionA11HaIp,
             cCdmaFailSessionA11FaIp,
             cCdmaFailSessionConnId,
             cCdmaFailSessionKey,
             cCdmaFailHistFailTime,
             cCdmaFailHistFailType,

             cCdmaRPRegValidRequests,
             cCdmaRPRegAcceptedReplies,
             cCdmaRPRegLifeTimeZeroRequests,
             cCdmaRPDeRegAcceptedReplies,
             cCdmaRPRegReasonUnSpecFailures,
             cCdmaRPRegAdminProhibFailures,
             cCdmaRPRegInsuffResFailures,
             cCdmaRPRegMNAuthenFailures,
             cCdmaRPRegIdentMismatchFailures,
             cCdmaRPRegBadRequestFailures,
             cCdmaRPRegUnknownHAAddrFailures,
             cCdmaRPRegNoRevTunnelFailures,
             cCdmaRPRegTBitNotSetFailures,
             cCdmaRPRegBadCVSEFailures,
             
             cCdmaRPUpdValidRequests,
             cCdmaRPUpdAcceptedReplies,
             cCdmaRPUpdAdminProhibFailures,
             cCdmaRPUpdMNAuthenFailures,
             cCdmaRPUpdIdentMismatchFailures,
             cCdmaRPUpdReasonUnSpecFailures, 
             cCdmaRPUpdBadRequestFailures
        }
         STATUS obsolete
         DESCRIPTION
                 "A collection of objects needed for PDSN network management."
         ::= { cCdmaPdsnMIBGroups 3 }

         cCdmaNotifPdsnGroupRev1  NOTIFICATION-GROUP
         NOTIFICATIONS
         {
             cCdmaSessionMaxAllowedNotif,
             cCdmaPcfMaxAllowedNotif,
             cCdmaSessionRegReqFailedNotif 
         }
         STATUS      deprecated -- superseded by cCdmaNotifPdsnGroupRev2
         DESCRIPTION
                 "The notifications related to PDSN network management."
         ::= { cCdmaPdsnMIBGroups 4 }

cCdmaSystemPdsnGroupRev2   OBJECT-GROUP
         OBJECTS {
            cCdmaSessionTotal,
            cCdmaSessionMaxAllowed,
            cCdmaPcfTotal,
            cCdmaPcfMaxAllowed,
            cCdmaSimpleIpFlowTotal,
            cCdmaMobileIpFlowTotal,
            cCdmaProxyMobileIpFlowTotal,
            cCdmaSessionFailTotal,
            cCdmaServingPdsnHostname,
            cCdmaSessionPdsnAuthenTimer,
            cCdmaSessionPdsnMaxFailHistory,
            cCdmaSessionMaxNotifEnabled,
            cCdmaPcfMaxAllowedNotifEnabled,
            cCdmaRegReqFailedNotifEnabled,
            cCdmaSystemVersion,
            cCdmaPcfSessionTotal,
            cCdmaPcfSessionMaxTotal,
            cCdmaPcfErrorTotal,
            cCdmaFailSessionMsid,
            cCdmaFailSessionMsidType,
            cCdmaFailSessionA11HaIp,
            cCdmaFailSessionA11FaIp,
            cCdmaFailSessionConnId,
            cCdmaFailSessionKey,
            cCdmaFailHistFailTime,
            cCdmaFailHistFailType,
            cCdmaRpRegReceivedReqs,
            cCdmaRpRegAcceptedReqs,
            cCdmaRpRegDeniedReqs,
            cCdmaRpRegDiscardedReqs,
            cCdmaRpInitRegAcceptedReqs,
            cCdmaRpInitRegDeniedReqs,
            cCdmaRpReRegAcceptedReqs,
            cCdmaRpReRegDeniedReqs,
            cCdmaRpDeRegAcceptedReqs,
            cCdmaRpDeRegDeniedReqs,
            cCdmaRpRegReasonlUnSpecFailures,
            cCdmaRpRegAdminProhibFailures,
            cCdmaRpRegInsuffResFailures,
            cCdmaRpRegMNAuthFailures,
            cCdmaRpRegIdMismatchFailures,
            cCdmaRpRegBadReqFailures,
            cCdmaRpRegUnknownPdsnFailures,
            cCdmaRpRegNoRevTunnelFailures,
            cCdmaRpRegTBitNotSetFailures,
            cCdmaRpRegBadCVSEFailures,
            cCdmaRpUpdTransmittedReqs,
            cCdmaRpUpdAcceptedReqs,
            cCdmaRpUpdDeniedReqs,
            cCdmaRpUpdNotAckedReqs,
            cCdmaRpUpdInitTransmittedReqs,
            cCdmaRpUpdReTransmittedReqs,
            cCdmaRpUpdReceivedAcks,
            cCdmaRpUpdDiscardedAcks,
            cCdmaRpUpdRpLifeExpReqs,
            cCdmaRpUpdPPPtermReqs,
            cCdmaRpUpdOtherReasonReqs,
            cCdmaRpUpdReasonUnSpecFailures,
            cCdmaRpUpdAdminProhibFailures,
            cCdmaRpUpdMNAuthenFailures,
            cCdmaRpUpdIdentMismatchFailures,
            cCdmaRpUpdBadReqFailures,
            cCdmaPppCurrentConnections,
            cCdmaPppConnectionInitiateReqs,
            cCdmaPppConnectionSuccesses,
            cCdmaPppConnectionFailures,
            cCdmaPppLcpFailures,
            cCdmaPppAuthFailures,
            cCdmaPppIpcpFailures,
            cCdmaPppEnterLcpNums,
            cCdmaPppEnterAuthNums,
            cCdmaPppEnterIpcpNums,
            cCdmaPppRenegTotalReqs,
            cCdmaPppRenegByPdsnReqs,
            cCdmaPppRenegByMobileReqs,
            cCdmaPppRenegLcpIpcpReqs,
            cCdmaPppRenegAddrMismatchReqs,
            cCdmaPppRenegOtherReasonReqs,
            cCdmaPppAuthChapAttempts,
            cCdmaPppAuthChapSuccesses,
            cCdmaPppAuthChapFailures,
            cCdmaPppAuthPapAttempts,
            cCdmaPppAuthPapSuccesses,
            cCdmaPppAuthPapFailures,
            cCdmaPppAuthMschapAttempts,
            cCdmaPppAuthMschapSuccesses,
            cCdmaPppAuthMschapFailures,
            cCdmaPppAuthEapAttempts,
            cCdmaPppAuthEapSuccesses,
            cCdmaPppAuthEapFailures,
            cCdmaPppTotalReleases,
            cCdmaPppPdsnReleases,
            cCdmaPppMobileReleases,
            cCdmaPppAddrFilterReleases,
            cCdmaPppAdminReleases,
            cCdmaPppLcpTermReleases,
            cCdmaPppIdleTimeoutReleases,
            cCdmaPppL2tpTunnelReleases,
            cCdmaPppInsufResReleases,
            cCdmaPppSessTimeoutReleases,
            cCdmaPppSrvIntReleases,
            cCdmaPppSrvUnavailReleases,
            cCdmaPppOtherReasonReleases,
            cCdmaPppCompressNegoCons,
            cCdmaPppCompressMsftCons,
            cCdmaPppCompressAscendCons,
            cCdmaPppCompressStackCons,
            cCdmaPppCompressDeflateCons,
            cCdmaPppCompressOtherCons,
            cCdmaPppNegoMrruCons,
            cCdmaPppNegoIpxCons,
            cCdmaPppNegoIpCons,
            cCdmaPppNegoVjCompCons,
            cCdmaPppNegoBapCons,
            cCdmaPppConFormedBundles,
            cCdmaTransmittedSipKiloOctets,
            cCdmaReceivedSipKiloOctets,
            cCdmaTransmittedSipPkts,
            cCdmaReceivedSipPkts,
            cCdmaTransmittedMipKiloOctets,
            cCdmaReceivedMipKiloOctets,
            cCdmaTransmittedMipPkts,
            cCdmaReceivedMipPkts,
            cCdmaTransmittedPmipKiloOctets,
            cCdmaReceivedPmipKiloOctets,
            cCdmaTransmittedPmipPkts,
            cCdmaReceivedPmipPkts,
            cCdmaFlowSimpleIpSuccesses,
            cCdmaFlowMobilIpSuccesses,
            cCdmaFlowProxyIpSuccesses,
            cCdmaFlowVpdnSuccesses
           }
         STATUS obsolete -- superceded by cCdmaSystemPdsnGroupRev3
         DESCRIPTION
                 "A collection of objects needed for PDSN R1.1 network 
                  management."
         ::= { cCdmaPdsnMIBGroups 5 }

cCdmaSystemPdsnGroupRev3 OBJECT-GROUP
         OBJECTS {
            cCdmaSessionTotal,
            cCdmaSessionMaxAllowed,
            cCdmaPcfTotal,
            cCdmaPcfMaxAllowed,
            cCdmaSimpleIpFlowTotal,
            cCdmaMobileIpFlowTotal,
            cCdmaProxyMobileIpFlowTotal,
            cCdmaSessionFailTotal,
            cCdmaServingPdsnHostname,
            cCdmaSessionPdsnAuthenTimer,
            cCdmaSessionPdsnMaxFailHistory,
            cCdmaSessionMaxNotifEnabled,
            cCdmaPcfMaxAllowedNotifEnabled,
            cCdmaRegReqFailedNotifEnabled,
            cCdmaSystemVersion,
            cCdmaSystemStatus,

            cCdmaPcfSessionTotal,
            cCdmaPcfSessionMaxTotal,
            cCdmaPcfErrorTotal,

            cCdmaFailSessionMsid,
            cCdmaFailSessionMsidType,
            cCdmaFailSessionEsn,
            cCdmaFailSessionA11HaIp,
            cCdmaFailSessionA11FaIp,
            cCdmaFailSessionConnId,
            cCdmaFailSessionKey,
            cCdmaFailHistFailTime,
            cCdmaFailHistFailType,

            cCdmaRpRegReceivedReqs,
            cCdmaRpRegAcceptedReqs,
            cCdmaRpRegDeniedReqs,
            cCdmaRpRegDiscardedReqs,
            cCdmaRpInitRegAcceptedReqs,
            cCdmaRpInitRegDeniedReqs,
            cCdmaRpReRegAcceptedReqs,
            cCdmaRpReRegDeniedReqs,
            cCdmaRpDeRegAcceptedReqs,
            cCdmaRpDeRegDeniedReqs,
            cCdmaRpRegReasonlUnSpecFailures,
            cCdmaRpRegAdminProhibFailures,
            cCdmaRpRegInsuffResFailures,
            cCdmaRpRegMNAuthFailures,
            cCdmaRpRegIdMismatchFailures,
            cCdmaRpRegBadReqFailures,
            cCdmaRpRegUnknownPdsnFailures,
            cCdmaRpRegNoRevTunnelFailures,
            cCdmaRpRegTBitNotSetFailures,
            cCdmaRpRegBadCVSEFailures,

            cCdmaRpUpdTransmittedReqs,
            cCdmaRpUpdAcceptedReqs,
            cCdmaRpUpdDeniedReqs,
            cCdmaRpUpdNotAckedReqs,
            cCdmaRpUpdInitTransmittedReqs,
            cCdmaRpUpdReTransmittedReqs,
            cCdmaRpUpdReceivedAcks,
            cCdmaRpUpdDiscardedAcks,
            cCdmaRpUpdRpLifeExpReqs,
            cCdmaRpUpdPPPtermReqs,
            cCdmaRpUpdOtherReasonReqs,
            cCdmaRpUpdReasonUnSpecFailures,
            cCdmaRpUpdAdminProhibFailures,
            cCdmaRpUpdMNAuthenFailures,
            cCdmaRpUpdIdentMismatchFailures,
            cCdmaRpUpdBadReqFailures,

            cCdmaPppCurrentConnections,
            cCdmaPppConnectionInitiateReqs,
            cCdmaPppConnectionSuccesses,
            cCdmaPppConnectionFailures,
            cCdmaPppLcpFailures,
            cCdmaPppAuthFailures,
            cCdmaPppIpcpFailures,
            cCdmaPppEnterLcpNums,
            cCdmaPppEnterAuthNums,
            cCdmaPppEnterIpcpNums,
            cCdmaPppRenegTotalReqs,
            cCdmaPppRenegByPdsnReqs,
            cCdmaPppRenegByMobileReqs,
            cCdmaPppRenegLcpIpcpReqs,
            cCdmaPppRenegAddrMismatchReqs,
            cCdmaPppRenegOtherReasonReqs,
            cCdmaPppAuthChapAttempts,
            cCdmaPppAuthChapSuccesses,
            cCdmaPppAuthChapFailures,
            cCdmaPppAuthPapAttempts,
            cCdmaPppAuthPapSuccesses,
            cCdmaPppAuthPapFailures,
            cCdmaPppAuthMschapAttempts,
            cCdmaPppAuthMschapSuccesses,
            cCdmaPppAuthMschapFailures,
            cCdmaPppAuthEapAttempts,
            cCdmaPppAuthEapSuccesses,
            cCdmaPppAuthEapFailures,
            cCdmaPppAuthMsidAttempts,
            cCdmaPppAuthMsidSuccesses,
            cCdmaPppAuthMsidFailures,
            cCdmaPppTotalReleases,
            cCdmaPppPdsnReleases,
            cCdmaPppMobileReleases,
            cCdmaPppAddrFilterReleases,
            cCdmaPppAdminReleases,
            cCdmaPppLcpTermReleases,
            cCdmaPppIdleTimeoutReleases,
            cCdmaPppL2tpTunnelReleases,
            cCdmaPppInsufResReleases,
            cCdmaPppSessTimeoutReleases,
            cCdmaPppSrvIntReleases,
            cCdmaPppSrvUnavailReleases,
            cCdmaPppOtherReasonReleases,
            cCdmaPppCompressNegoCons,
            cCdmaPppCompressMsftCons,
            cCdmaPppCompressAscendCons,
            cCdmaPppCompressStackCons,
            cCdmaPppCompressDeflateCons,
            cCdmaPppCompressOtherCons,
            cCdmaPppNegoMrruCons,
            cCdmaPppNegoIpxCons,
            cCdmaPppNegoIpCons,
            cCdmaPppNegoVjCompCons,
            cCdmaPppNegoBapCons,
            cCdmaPppConFormedBundles,
            cCdmaTransmittedSipKiloOctets,
            cCdmaReceivedSipKiloOctets,
            cCdmaTransmittedSipPkts,
            cCdmaReceivedSipPkts,
            cCdmaTransmittedMipKiloOctets,
            cCdmaReceivedMipKiloOctets,
            cCdmaTransmittedMipPkts,
            cCdmaReceivedMipPkts,
            cCdmaTransmittedPmipKiloOctets,
            cCdmaReceivedPmipKiloOctets,
            cCdmaTransmittedPmipPkts,
            cCdmaReceivedPmipPkts,

            cCdmaFlowSimpleIpSuccesses,
            cCdmaFlowMobilIpSuccesses,
            cCdmaFlowProxyIpSuccesses,
            cCdmaFlowVpdnSuccesses,
            cCdmaFlowSimpleIpFailures,
            cCdmaFlowMobileIpFailures,
            cCdmaFlowProxyIpFailures,
            cCdmaFlowVpdnFailures,
            cCdmaFlowUnknownTypeFailures ,


            cCdmaServiceTotalOptions,
            cCdmaServiceOptionSucesses,
            cCdmaServiceOptionFailures,

            cCdmaInterPcfHandoffs,
            cCdmaInterPdsnHandoffs,
            cCdmaIdChangeHandoffs,

            cCdmaStatusIS2OOSes,
            cCdmaStatusOOS2ISes,

            cCdmaAddressStaticSIPs,
            cCdmaAddressDynamicSIPs,
            cCdmaAddressStaticMIPs,
            cCdmaAddressDynamicMIPs,
            cCdmaAddressStaticPMIPs,
            cCdmaAddressDynamicPMIPs,
            cCdmaAddressStaticVPDNs,
            cCdmaAddressDynamicVPDNs,
            
            cCdmaSessionHighThreshold,
            cCdmaSessionLowThreshold,

            cCdmaClusterType,
            cCdmaClusterRole,
            cCdmaClusterTotalControllers,
            cCdmaClusterCtrlStatus,

            cCdmaClusterSessHighThreshold,
            cCdmaClusterSessLowThreshold,
            cCdmaClusterTotalSessions,
            cCdmaClusterTotalMembers,
            cCdmaClusterMemberStatus,
            cCdmaClusterMemberLoad,
            cCdmaNotifSeverityLevel,
            cCdmaServiceAffectedLevel,
            cCdmaAffectedAddress,
            cCdmaAffectedAddressType,
            cCdmaAffectedMemberStatus, 
            cCdmaAffectedCtrlStatus
         }
         STATUS deprecated -- superceded by cCdmaSystemPdsnGroupRev4
         DESCRIPTION
                 "A collection of objects needed for PDSN R1.2 network
                  management."
         ::= { cCdmaPdsnMIBGroups 6 }

cCdmaNotifPdsnGroupRev2  NOTIFICATION-GROUP
         NOTIFICATIONS
         {
             cCdmaSessionMaxAllowedNotif,
             cCdmaPcfMaxAllowedNotif,
             cCdmaSessionRegReqFailedNotif,
             cCdmaPdsnStatusChange,
             cCdmaSessionHighReached,
             cCdmaSessionLowReached,
             cCdmaClusterSessionHighReached,
             cCdmaClusterSessionLowReached,
             cCdmaClusterMemberStatusChange,
             cCdmaClusterCtrlStatusChange
         }
         STATUS      deprecated -- superceded by cCdmaNotifPdsnGroupRev3
         DESCRIPTION
                 "The notifications related to PDSN R1.2 network
                  management."
         ::= { cCdmaPdsnMIBGroups 7 }

cCdmaSystemPdsnGroupRev4 OBJECT-GROUP
         OBJECTS {
            cCdmaSessionTotal,
            cCdmaSessionMaxAllowed,
            cCdmaPcfTotal,
            cCdmaPcfMaxAllowed,
            cCdmaSimpleIpFlowTotal,
            cCdmaMobileIpFlowTotal,
            cCdmaProxyMobileIpFlowTotal,
            cCdmaSessionFailTotal,
            cCdmaServingPdsnHostname,
            cCdmaSessionPdsnAuthenTimer,
            cCdmaSessionPdsnMaxFailHistory,
            cCdmaSessionMaxNotifEnabled,
            cCdmaPcfMaxAllowedNotifEnabled,
            cCdmaRegReqFailedNotifEnabled,
            cCdmaSystemVersion,
            cCdmaSystemStatus,

            cCdmaPcfSessionTotal,
            cCdmaPcfSessionMaxTotal,
            cCdmaPcfErrorTotal,

            cCdmaFailSessionMsid,
            cCdmaFailSessionMsidType,
            cCdmaFailSessionEsn,
            cCdmaFailSessionA11HaIp,
            cCdmaFailSessionA11FaIp,
            cCdmaFailSessionConnId,
            cCdmaFailSessionKey,
            cCdmaFailHistFailTime,
            cCdmaFailHistFailType,
            cCdmaFailHistServiceOption,
            cCdmaFailHistPanId,
            cCdmaFailHistCanId,
            cCdmaFailHistBsid,

            cCdmaRpRegReceivedReqs,
            cCdmaRpRegAcceptedReqs,
            cCdmaRpRegDeniedReqs,
            cCdmaRpRegDiscardedReqs,
            cCdmaRpInitRegAcceptedReqs,
            cCdmaRpInitRegDeniedReqs,
            cCdmaRpReRegAcceptedReqs,
            cCdmaRpReRegDeniedReqs,
            cCdmaRpDeRegAcceptedReqs,
            cCdmaRpDeRegDeniedReqs,
            cCdmaRpRegReasonlUnSpecFailures,
            cCdmaRpRegAdminProhibFailures,
            cCdmaRpRegInsuffResFailures,
            cCdmaRpRegMNAuthFailures,
            cCdmaRpRegIdMismatchFailures,
            cCdmaRpRegBadReqFailures,
            cCdmaRpRegUnknownPdsnFailures,
            cCdmaRpRegNoRevTunnelFailures,
            cCdmaRpRegTBitNotSetFailures,
            cCdmaRpRegBadCVSEFailures,

            cCdmaRpUpdTransmittedReqs,
            cCdmaRpUpdAcceptedReqs,
            cCdmaRpUpdDeniedReqs,
            cCdmaRpUpdNotAckedReqs,
            cCdmaRpUpdInitTransmittedReqs,
            cCdmaRpUpdReTransmittedReqs,
            cCdmaRpUpdReceivedAcks,
            cCdmaRpUpdDiscardedAcks,
            cCdmaRpUpdRpLifeExpReqs,
            cCdmaRpUpdPPPtermReqs,
            cCdmaRpUpdOtherReasonReqs,
            cCdmaRpUpdReasonUnSpecFailures,
            cCdmaRpUpdAdminProhibFailures,
            cCdmaRpUpdMNAuthenFailures,
            cCdmaRpUpdIdentMismatchFailures,
            cCdmaRpUpdBadReqFailures,
            
            cCdmaPppCurrentConnections,
            cCdmaPppConnectionInitiateReqs,
            cCdmaPppConnectionSuccesses,
            cCdmaPppConnectionFailures,
            cCdmaPppLcpFailures,
            cCdmaPppAuthFailures,
            cCdmaPppIpcpFailures,
            cCdmaPppEnterLcpNums,
            cCdmaPppEnterAuthNums,
            cCdmaPppEnterIpcpNums,
            cCdmaPppLcpFailuresMaxRetrans,
            cCdmaPppLcpFailuresUnknown,
            cCdmaPppIpcpFailuresMaxRetrans,
            cCdmaPppIpcpFailuresUnknown,
            cCdmaPppConnectionsAborted,
            cCdmaPppRenegTotalReqs,
            cCdmaPppRenegByPdsnReqs,
            cCdmaPppRenegByMobileReqs,
            cCdmaPppRenegLcpIpcpReqs,
            cCdmaPppRenegAddrMismatchReqs,
            cCdmaPppRenegOtherReasonReqs,
            cCdmaPppRenegSuccesses,
            cCdmaPppRenegFailures,
            cCdmaPppRenegConnectionsAborted,            
            cCdmaPppAuthChapAttempts,
            cCdmaPppAuthChapSuccesses,
            cCdmaPppAuthChapFailures,
            cCdmaPppAuthPapAttempts,
            cCdmaPppAuthPapSuccesses,
            cCdmaPppAuthPapFailures,
            cCdmaPppAuthMschapAttempts,
            cCdmaPppAuthMschapSuccesses,
            cCdmaPppAuthMschapFailures,
            cCdmaPppAuthEapAttempts,
            cCdmaPppAuthEapSuccesses,
            cCdmaPppAuthEapFailures,
            cCdmaPppAuthMsidAttempts,
            cCdmaPppAuthMsidSuccesses,
            cCdmaPppAuthMsidFailures,
            cCdmaPppTotalReleases,
            cCdmaPppPdsnReleases,
            cCdmaPppMobileReleases,
            cCdmaPppAddrFilterReleases,
            cCdmaPppAdminReleases,
            cCdmaPppLcpTermReleases,
            cCdmaPppIdleTimeoutReleases,
            cCdmaPppL2tpTunnelReleases,
            cCdmaPppInsufResReleases,
            cCdmaPppSessTimeoutReleases,
            cCdmaPppSrvIntReleases,
            cCdmaPppSrvUnavailReleases,
            cCdmaPppOtherReasonReleases,
            cCdmaPppCompressNegoCons,
            cCdmaPppCompressMsftCons,
            cCdmaPppCompressAscendCons,
            cCdmaPppCompressStackCons,
            cCdmaPppCompressDeflateCons,
            cCdmaPppCompressOtherCons,
            cCdmaPppNegoMrruCons,
            cCdmaPppNegoIpxCons,
            cCdmaPppNegoIpCons,
            cCdmaPppNegoVjCompCons,
            cCdmaPppNegoBapCons,
            cCdmaPppConFormedBundles,
            cCdmaTransmittedSipKiloOctets,
            cCdmaReceivedSipKiloOctets,
            cCdmaTransmittedSipPkts,
            cCdmaReceivedSipPkts,
            cCdmaTransmittedMipKiloOctets,
            cCdmaReceivedMipKiloOctets,
            cCdmaTransmittedMipPkts,
            cCdmaReceivedMipPkts,
            cCdmaTransmittedPmipKiloOctets,
            cCdmaReceivedPmipKiloOctets,
            cCdmaTransmittedPmipPkts,
            cCdmaReceivedPmipPkts,

            cCdmaFlowSimpleIpSuccesses,
            cCdmaFlowMobilIpSuccesses,
            cCdmaFlowProxyIpSuccesses,
            cCdmaFlowVpdnSuccesses,
            cCdmaFlowSimpleIpFailures,
            cCdmaFlowMobileIpFailures,
            cCdmaFlowProxyIpFailures,
            cCdmaFlowVpdnFailures,
            cCdmaFlowUnknownTypeFailures ,


            cCdmaServiceTotalOptions,
            cCdmaServiceOptionSucesses,
            cCdmaServiceOptionFailures,

            cCdmaInterPcfHandoffs,
            cCdmaInterPdsnHandoffs,
            cCdmaIdChangeHandoffs,

            cCdmaStatusIS2OOSes,
            cCdmaStatusOOS2ISes,

            cCdmaAddressStaticSIPs,
            cCdmaAddressDynamicSIPs,
            cCdmaAddressStaticMIPs,
            cCdmaAddressDynamicMIPs,
            cCdmaAddressStaticPMIPs,
            cCdmaAddressDynamicPMIPs,
            cCdmaAddressStaticVPDNs,
            cCdmaAddressDynamicVPDNs,
            
            cCdmaSessionHighThreshold,
            cCdmaSessionLowThreshold,

            cCdmaClusterType,
            cCdmaClusterRole,
            cCdmaClusterTotalControllers,
            cCdmaClusterCtrlStatus,

            cCdmaClusterSessHighThreshold,
            cCdmaClusterSessLowThreshold,
            cCdmaClusterTotalSessions,
            cCdmaClusterTotalMembers,
            cCdmaClusterMemberStatus,
            cCdmaClusterMemberLoad,
            cCdmaNotifSeverityLevel,
            cCdmaServiceAffectedLevel,
            cCdmaAffectedAddress,
            cCdmaAffectedAddressType,
            cCdmaAffectedMemberStatus, 
            cCdmaAffectedCtrlStatus
         }
         STATUS deprecated -- superceded by cCdmaSystemPdsnGroupRev5
         DESCRIPTION
                 "A collection of objects needed for PDSN R1.2 network
                  management."
         ::= { cCdmaPdsnMIBGroups 8 }

cCdmaPdsnPcfSoRpRegGroup OBJECT-GROUP
         OBJECTS {
             cCdmaPcfSoRpRegRcvdReqs,
             cCdmaPcfSoRpRegAcptdReqs,
             cCdmaPcfSoRpRegDeniedReqs,
             cCdmaPcfSoRpRegDiscardedReqs,
             cCdmaPcfSoRpInitRegAcptdReqs,
             cCdmaPcfSoRpInitRegDeniedReqs,
             cCdmaPcfSoRpReRegAcptdReqs,
             cCdmaPcfSoRpReRegDeniedReqs,
             cCdmaPcfSoRpDeRegAcptdReqs,
             cCdmaPcfSoRpDeRegDeniedReqs,
             cCdmaPcfSoRpRegPcfUnknwnFails,
             cCdmaPcfSoRpRegAdmnFails,
             cCdmaPcfSoRpRegNoRsrcFails,
             cCdmaPcfSoRpRegMNAuthFails,
             cCdmaPcfSoRpRegIdMismatFails,
             cCdmaPcfSoRpRegBadReqFails,
             cCdmaPcfSoRpRegUnkPdsnFails,
             cCdmaPcfSoRpRegNoRevTunFails,
             cCdmaPcfSoRpRegTBitNSetFails,
             cCdmaPcfSoRpRegBadCVSEFails,

             cCdmaPcfSoRpUpdTxdReqs,
             cCdmaPcfSoRpUpdAcptdReqs,
             cCdmaPcfSoRpUpdDeniedReqs,
             cCdmaPcfSoRpUpdNotAckedReqs,
             cCdmaPcfSoRpUpdInitTxdReqs,
             cCdmaPcfSoRpUpdReTxdReqs,
             cCdmaPcfSoRpUpdRcvdAcks,
             cCdmaPcfSoRpUpdDiscardedAcks,
             cCdmaPcfSoRpUpdRpLifeExpReqs,
             cCdmaPcfSoRpUpdPPPtermReqs,
             cCdmaPcfSoRpUpdOtherReaReqs,
             cCdmaPcfSoRpUpdReaUnSpecFails,
             cCdmaPcfSoRpUpdAdmnFails,
             cCdmaPcfSoRpUpdMNAuthFails,
             cCdmaPcfSoRpUpdIdMismatFails,
             cCdmaPcfSoRpUpdBadReqFails
         }
         STATUS current
         DESCRIPTION
                 "A collection of RP registration statistics 
                  MIB objects needed for R2.0 PDSN management."
         ::= { cCdmaPdsnMIBGroups 9 }         
         
cCdmaPdsnPcfSoPppGroup OBJECT-GROUP
         OBJECTS {
             cCdmaPcfSoPppCurrentConns,
             cCdmaPcfSoPppConnInitiateReqs,
             cCdmaPcfSoPppConnSuccesses,
             cCdmaPcfSoPppConnFails,
             cCdmaPcfSoPppConnAborts
         }
         STATUS current
         DESCRIPTION
                 "A collection PPP negotiation statistics MIB
                  objects needs for R2.0 PDSN management."
         ::= { cCdmaPdsnMIBGroups 10 }

cCdmaNotifPdsnGroupRev3  NOTIFICATION-GROUP
         NOTIFICATIONS
         {
             cCdmaSessionMaxAllowedNotif,
             cCdmaPcfMaxAllowedNotif,
             cCdmaSessionRegReqFailedNotif,
             cCdmaPdsnStatusChange,
             cCdmaSessionHighReached,
             cCdmaSessionLowReached2,
             cCdmaClusterSessionHighReached,
             cCdmaClusterSessionLowReached,
             cCdmaClusterMemberStatusChange2,
             cCdmaClusterCtrlStatusChange2
         }
         STATUS      current
         DESCRIPTION
                 "The notifications related to PDSN R1.2 network
                  management."
         ::= { cCdmaPdsnMIBGroups 11 }

cCdmaSystemPdsnGroupRev5 OBJECT-GROUP
         OBJECTS {
            cCdmaSessionTotal,
            cCdmaSessionMaxAllowed,
            cCdmaPcfTotal,
            cCdmaPcfMaxAllowed,
            cCdmaSimpleIpFlowTotal,
            cCdmaMobileIpFlowTotal,
            cCdmaProxyMobileIpFlowTotal,
            cCdmaSessionFailTotal,
            cCdmaServingPdsnHostname,
            cCdmaSessionPdsnAuthenTimer,
            cCdmaSessionPdsnMaxFailHistory,
            cCdmaSessionMaxNotifEnabled,
            cCdmaPcfMaxAllowedNotifEnabled,
            cCdmaRegReqFailedNotifEnabled,
            cCdmaSystemVersion,
            cCdmaSystemStatus,
            cCdmaSrEnabled,
            cCdmaActiveSessions,
            cCdmaDormantSessions,

            cCdmaPcfSessionTotal,
            cCdmaPcfSessionMaxTotal,
            cCdmaPcfErrorTotal,

            cCdmaFailSessionMsid,
            cCdmaFailSessionMsidType,
            cCdmaFailSessionA11HaIp,
            cCdmaFailSessionA11FaIp,
            cCdmaFailSessionConnId,
            cCdmaFailSessionKey,
            cCdmaFailHistFailTime,
            cCdmaFailHistFailType,
            cCdmaFailHistServiceOption,
            cCdmaFailHistPanId,
            cCdmaFailHistCanId,
            cCdmaFailHistBsid,
            cCdmaFailSessionEsn2,

            cCdmaRpRegReceivedReqs,
            cCdmaRpRegAcceptedReqs,
            cCdmaRpRegDeniedReqs,
            cCdmaRpRegDiscardedReqs,
            cCdmaRpInitRegAcceptedReqs,
            cCdmaRpInitRegDeniedReqs,
            cCdmaRpReRegAcceptedReqs,
            cCdmaRpReRegDeniedReqs,
            cCdmaRpDeRegAcceptedReqs,
            cCdmaRpDeRegDeniedReqs,
            cCdmaRpRegReasonUnSpecFailures,
            cCdmaRpRegAdminProhibFailures,
            cCdmaRpRegInsuffResFailures,
            cCdmaRpRegMNAuthFailures,
            cCdmaRpRegIdMismatchFailures,
            cCdmaRpRegBadReqFailures,
            cCdmaRpRegUnknownPdsnFailures,
            cCdmaRpRegNoRevTunnelFailures,
            cCdmaRpRegTBitNotSetFailures,
            cCdmaRpRegBadCVSEFailures,

            cCdmaRpUpdTransmittedReqs,
            cCdmaRpUpdAcceptedReqs,
            cCdmaRpUpdDeniedReqs,
            cCdmaRpUpdNotAckedReqs,
            cCdmaRpUpdInitTransmittedReqs,
            cCdmaRpUpdReTransmittedReqs,
            cCdmaRpUpdReceivedAcks,
            cCdmaRpUpdDiscardedAcks,
            cCdmaRpUpdRpLifeExpReqs,
            cCdmaRpUpdPPPtermReqs,
            cCdmaRpUpdOtherReasonReqs,
            cCdmaRpUpdReasonUnSpecFailures,
            cCdmaRpUpdAdminProhibFailures,
            cCdmaRpUpdMNAuthenFailures,
            cCdmaRpUpdIdentMismatchFailures,
            cCdmaRpUpdBadReqFailures,
            
            cCdmaPppCurrentConnections,
            cCdmaPppConnectionInitiateReqs,
            cCdmaPppConnectionSuccesses,
            cCdmaPppConnectionFailures,
            cCdmaPppLcpFailures,
            cCdmaPppAuthFailures,
            cCdmaPppIpcpFailures,
            cCdmaPppEnterLcpNums,
            cCdmaPppEnterAuthNums,
            cCdmaPppEnterIpcpNums,
            cCdmaPppLcpFailuresMaxRetrans,
            cCdmaPppLcpFailuresUnknown,
            cCdmaPppIpcpFailuresMaxRetrans,
            cCdmaPppIpcpFailuresUnknown,
            cCdmaPppConnectionsAborted,
            cCdmaPppRenegTotalReqs,
            cCdmaPppRenegByPdsnReqs,
            cCdmaPppRenegByMobileReqs,
            cCdmaPppRenegLcpIpcpReqs,
            cCdmaPppRenegAddrMismatchReqs,
            cCdmaPppRenegOtherReasonReqs,
            cCdmaPppRenegSuccesses,
            cCdmaPppRenegFailures,
            cCdmaPppRenegConnectionsAborted,            
            cCdmaPppAuthChapAttempts,
            cCdmaPppAuthChapSuccesses,
            cCdmaPppAuthChapFailures,
            cCdmaPppAuthPapAttempts,
            cCdmaPppAuthPapSuccesses,
            cCdmaPppAuthPapFailures,
            cCdmaPppAuthMschapAttempts,
            cCdmaPppAuthMschapSuccesses,
            cCdmaPppAuthMschapFailures,
            cCdmaPppAuthEapAttempts,
            cCdmaPppAuthEapSuccesses,
            cCdmaPppAuthEapFailures,
            cCdmaPppAuthMsidAttempts,
            cCdmaPppAuthMsidSuccesses,
            cCdmaPppAuthMsidFailures,
            cCdmaPppAuthAAATimeouts,
            cCdmaPppTotalReleases,
            cCdmaPppPdsnReleases,
            cCdmaPppMobileReleases,
            cCdmaPppAddrFilterReleases,
            cCdmaPppAdminReleases,
            cCdmaPppIdleTimeoutReleases,
            cCdmaPppL2tpTunnelReleases,
            cCdmaPppSessTimeoutReleases,
            cCdmaPppSrvIntReleases,
            cCdmaPppSrvUnavailReleases,
            cCdmaPppOtherReasonReleases,
            cCdmaPppMissEchoReleases,
            cCdmaPppCompressNegoCons,
            cCdmaPppCompressMsftCons,
            cCdmaPppCompressAscendCons,
            cCdmaPppCompressStackCons,
            cCdmaPppCompressDeflateCons,
            cCdmaPppCompressOtherCons,
            cCdmaPppNegoMrruCons,
            cCdmaPppNegoIpxCons,
            cCdmaPppNegoIpCons,
            cCdmaPppNegoVjCompCons,
            cCdmaPppNegoBapCons,
            cCdmaPppConFormedBundles,
            cCdmaTransmittedSipKiloOctets,
            cCdmaReceivedSipKiloOctets,
            cCdmaTransmittedSipPkts,
            cCdmaReceivedSipPkts,
            cCdmaTransmittedMipKiloOctets,
            cCdmaReceivedMipKiloOctets,
            cCdmaTransmittedMipPkts,
            cCdmaReceivedMipPkts,
            cCdmaTransmittedPmipKiloOctets,
            cCdmaReceivedPmipKiloOctets,
            cCdmaTransmittedPmipPkts,
            cCdmaReceivedPmipPkts,

            cCdmaFlowSimpleIpSuccesses,
            cCdmaFlowMobilIpSuccesses,
            cCdmaFlowProxyIpSuccesses,
            cCdmaFlowVpdnSuccesses,
            cCdmaFlowSimpleIpFailures,
            cCdmaFlowMobileIpFailures,
            cCdmaFlowProxyIpFailures,
            cCdmaFlowVpdnFailures,
            cCdmaFlowUnknownTypeFailures,

            cCdmaServiceTotalOptions,
            cCdmaServiceOptionSucesses,
            cCdmaServiceOptionFailures,

            cCdmaInterPcfHandoffs,
            cCdmaInterPdsnHandoffs,
            cCdmaIdChangeHandoffs,
            cCdmaRpUpdPcfHandoffs,
            cCdmaRpUpdHandoffNotAckedReqs,
            cCdmaRpUpdHandoffInitTxdReqs,
            cCdmaRpUpdHandoffReTxdReqs,
            cCdmaRpUpdHandoffReceivedAcks,
            cCdmaRpUpdHandoffDiscardedAcks,
            cCdmaRpUpdHandoffReaUnSpecFails,
            cCdmaRpUpdHandoffAdmProhibFails,
            cCdmaRpUpdHandoffMNAuthenFails,
            cCdmaRpUpdHandoffIdMismatchFails,
            cCdmaRpUpdHandoffBadReqFails,
            cCdmaRpUpdHandoffAcceptedReqs,
            cCdmaRpUpdHandoffDeniedReqs,
            cCdmaRpDeRegHandoffAcceptedReqs,
            cCdmaRpDeRegHandoffDeniedReqs,

            cCdmaStatusIS2OOSes,
            cCdmaStatusOOS2ISes,

            cCdmaAddressStaticSIPs,
            cCdmaAddressDynamicSIPs,
            cCdmaAddressStaticMIPs,
            cCdmaAddressDynamicMIPs,
            cCdmaAddressStaticPMIPs,
            cCdmaAddressDynamicPMIPs,
            cCdmaAddressStaticVPDNs,
            cCdmaAddressDynamicVPDNs,
            
            cCdmaSessionHighThreshold,
            cCdmaSessionLowThreshold,

            cCdmaClusterType,
            cCdmaClusterRole,
            cCdmaClusterTotalControllers,
            cCdmaClusterCtrlStatus,

            cCdmaClusterSessHighThreshold,
            cCdmaClusterSessLowThreshold,
            cCdmaClusterTotalSessions,
            cCdmaClusterTotalMembers,
            cCdmaClusterMemberStatus,
            cCdmaClusterMemberLoad,
            cCdmaNotifSeverityLevel,
            cCdmaServiceAffectedLevel
         }
         STATUS current
         DESCRIPTION
                 "A collection of objects needed for PDSN R1.2 network
                  management."
         ::= { cCdmaPdsnMIBGroups 12 }

cCdmaSystemPdsnGroupSup1 OBJECT-GROUP
         OBJECTS {
            cCdmaPPPoGRESessionTotal,
            cCdmaHDLCoGRESessionTotal,        
            cCdmaEstablishedSessions,
            cCdmaReleasedSessions,
            cCdmaMSIDFlowTotal,
            cCdmaVPDNFlowTotal,

            cCdmaRpInitRegReceivedReqs,
            cCdmaRpInitRegDiscardedReqs,
            cCdmaRpReRegReceivedReqs,
            cCdmaRpReRegDiscardedReqs,
            cCdmaRpReRegAirlinkStarts,
            cCdmaRpReRegAirlinkStops,
            cCdmaRpDeRegReceivedReqs,
            cCdmaRpDeRegDiscardedReqs,
            cCdmaRpDeRegAirlinkStops,
            cCdmaRpHandoffRegReceivedReqs,
            cCdmaRpHandoffRegAcceptedReqs,
            cCdmaRpHandoffRegDeniedReqs,
            cCdmaRpHandoffRegDiscardedReqs,

            cCdmaRpSessUpdTransmittedReqs,
            cCdmaRpSessUpdAcceptedReqs,
            cCdmaRpSessUpdDeniedReqs,
            cCdmaRpSessUpdNotAckedReqs,
            cCdmaRpSessUpdInitTransmittedReqs,
            cCdmaRpSessUpdReTransmittedReqs,
            cCdmaRpSessUpdReceivedAcks,
            cCdmaRpSessUpdDiscardedAcks,
            cCdmaRpSessUpdAlwaysON,
            cCdmaRpSessUpdRNPDIT,
            cCdmaRpSessUpdReasonParamNotUpdated,
            cCdmaRpSessUpdReasonUnSpecFailures,
            cCdmaRpSessUpdMNAuthenFailures,
            cCdmaRpSessUpdIdentMismatchFailures,
            cCdmaRpSessUpdBadReqFailures,
            
            cCdmaPppLcpOptionIssueFailures,
            cCdmaPppIpcpOptionIssueFailures,
            cCdmaPppAuthMaxRetransFailures,
            cCdmaPppNoRemoteIpAddressReleases, 
            cCdmaPppLowerLayerReleaseFailures,
            cCdmaPppIpcpPhaseReceivedTermreqs,
            cCdmaPppIpcpPhaseSentTermreqs,
            cCdmaPppAuthPhaseReceivedTermreqs,
            cCdmaPppAuthPhaseSentTermreqs,
            cCdmaPppLcpPhaseReceivedTermreqs,
            cCdmaPppLcpPhaseSentTermreqs,
            cCdmaPppPreLCPPdsnA10Releases,
            cCdmaPppPreLCPPcfA10Releases,
            cCdmaPppLCPPdsnA10Releases,
            cCdmaPppLCPPcfA10Releases,
            cCdmaPppAuthPdsnA10Releases,
            cCdmaPppAuthPcfA10Releases,
            cCdmaPppIPCPPdsnA10Releases,
            cCdmaPppIPCPPcfA10Releases,
            cCdmaPppLcpSuccesses,
            cCdmaPppIpcpSuccesses,
            cCdmaPppAuthSuccesses,
            cCdmaPppConnectionOtherFailures,
            cCdmaPppRenegAnidChanges,
            cCdmaPppAuthChapTimeouts,
            cCdmaPppAuthPapTimeouts,
            cCdmaPppAuthMschapTimeouts,
            cCdmaPppAuthSkips,
            cCdmaPppDeregisterByPcfReleases,
            cCdmaPppLifetimeExpiryReleases,
            cCdmaPppCompressNegoFailures,
            cCdmaPppTransmittedEchoReqs,
            cCdmaPppRetransmittedEchoReqs,
            cCdmaPppReceivedEchoReplies,
            cCdmaPppEchoRequestTimeouts,
            cCdmaPppUnknownProtocolPktDiscards,
            cCdmaPppBadLengthPktDiscards,
            cCdmaTransmittedSDBPkts,
            cCdmaTransmittedSDBOctets,
            cCdmaNoGREKeyPktDiscards,
            cCdmaNoSessionPktDiscards,
            cCdmaInvGREProtoPktDiscards,
            cCdmaInvCheckSumPktDiscards,

            cCdmaRpInterPCFActiveHandoffs,
            cCdmaRpInterPCFDormantHandoffs,

            cCdmaRegReqInvPakLenErrs,
            cCdmaRegReqInvProtocolErrs,
            cCdmaRegReqInvFlagsErrs,
            cCdmaRegReqInvMHAEKeyErrs,
            cCdmaRegReqMismatchSPIErrs,
            cCdmaRegReqInvSPIErrs,
            cCdmaRegReqInvConnectionIDErrs,
            cCdmaRegReqInvMNIDErrs,
            cCdmaRegReqInvMNIDTypeErrs,
            cCdmaRegReqInvMSIDLenErrs,
            cCdmaRegReqMissingSSEErrs,
            cCdmaRegReqMissingMHAEErrs,
            cCdmaRegReqInvOrderErrs,
            cCdmaRegReqInvVSEErrs,
            cCdmaRegReqInvAppTypeInVSEErrs,
            cCdmaRegReqDupAppTypeInVSEErrs,
            cCdmaRegReqInvAppSubTypeInVSEErrs,
            cCdmaRegReqInvVendorIDInVSEErrs,
            cCdmaRegReqDupCVSEErrs,
            cCdmaRegReqAcctUnknwnAttrErrs,
            cCdmaRegReqAcctInvLenAttrErrs,
            cCdmaRegReqAcctDupAttrErrs,
            cCdmaRegReqAcctRecRetransErrs,
            cCdmaRegReqAcctInvSeqNumErrs,
            cCdmaRegReqDuplicateGREKeyErrs,
            cCdmaRegReqSameGREKeySetupRcvdErrs,
            cCdmaRegReqGREKeyChngNoSetupErrs,
            cCdmaRegReqInitNoSetupErrs,
            cCdmaRegReqStartBeforeSetupErrs,
            cCdmaRegReqStartOnCloseErrs,
            cCdmaRegReqStartOnActiveErrs,
            cCdmaRegReqStopOnDormantErrs,
            cCdmaRegReqInitRcvdStopErrs,
            cCdmaRegReqInitRcvdSDBErrs,
            cCdmaRegReqInvAirlinkRecErrs,
            cCdmaRegReqDeRegNoSessionErrs,
            cCdmaRegReqReRegInDisconnectErrs,
            cCdmaRegReqMemFailErrs,
            cCdmaRpRegReqMaxSessionReachedErrs,
            cCdmaRegUpdAckInvPakLenErrs,
            cCdmaRegUpdAckInvProtocolErrs,
            cCdmaRegUpdAckInvRUAEKeyErrs,
            cCdmaRegUpdAckInvSPIErrs,
            cCdmaRegUpdAckInvConnectionIDErrs,
            cCdmaRegUpdAckInvMNIDErrs,
            cCdmaRegUpdAckInvMNIDTypeErrs,
            cCdmaRegUpdAckInvMSIDLenErrs,
            cCdmaRegUpdAckMissingSSEErrs,
            cCdmaRegUpdAckMissingRUAEErrs,
            cCdmaRegUpdAckInvOrderErrs,
            cCdmaRegUpdAckInvVSEErrs,
            cCdmaRegUpdAckNoSessionErrs,
            cCdmaRegUpdAckMemFailErrs,
            cCdmaSessUpdAckInvPakLenErrs,
            cCdmaSessUpdAckInvProtocolErrs,
            cCdmaSessUpdAckInvRUAEKeyErrs,
            cCdmaSessUpdAckInvSPIErrs,
            cCdmaSessUpdAckInvConnectionIDErrs,
            cCdmaSessUpdAckInvMNIDErrs,
            cCdmaSessUpdAckInvMNIDTypeErrs,
            cCdmaSessUpdAckInvMSIDLenErrs,
            cCdmaSessUpdAckMissingSSEErrs,
            cCdmaSessUpdAckMissingRUAEErrs,
            cCdmaSessUpdAckInvOrderErrs,
            cCdmaSessUpdAckInvVSEErrs,
            cCdmaSessUpdAckNoSessionErrs,
            cCdmaSessUpdAckMemFailErrs,
            cCdmaRegRplyInternalErrs,
            cCdmaRegRplyMemFailErrs,
            cCdmaRpRplyPCFNoSecOrParseErrs,
            cCdmaRegUpdInternalErrs,
            cCdmaRegUpdMemFailErrs,
            cCdmaSessUpdInternalErrs,
            cCdmaSessUpdMemFailErrs
         }
         STATUS current
         DESCRIPTION
                 "A collection of objects added for PDSN R3.0 that
                  supplements cCdmaSystemPdsnGroupRev5 objects."
         ::= { cCdmaPdsnMIBGroups 13 }

cCdmaPdsnPcfSoRpRegGroupSup1 OBJECT-GROUP
         OBJECTS {
             cCdmaPcfSoRpInitRegRcvdReqs,
             cCdmaPcfSoRpInitRegDiscardedReqs,
             cCdmaPcfSoRpReRegRcvdReqs,
             cCdmaPcfSoRpReRegDiscardedReqs,
             cCdmaPcfSoRpDeRegRcvdReqs,
             cCdmaPcfSoRpDeRegDiscardedReqs,
             cCdmaPcfSoRpHandoffRegRcvdReqs,
             cCdmaPcfSoRpHandoffRegAcptdReqs,
             cCdmaPcfSoRpHandoffRegDeniedReqs,
             cCdmaPcfSoRpHandoffRegDiscardedReqs,
             cCdmaPcfSoRpReRegAirlinkStarts,
             cCdmaPcfSoRpReRegAirlinkStops,
             cCdmaPcfSoRpDeRegAirlinkStops,

             cCdmaSoRpUpdPcfHandoffs,
             cCdmaSoRpUpdHandoffNotAckedReqs,
             cCdmaSoRpUpdHandoffReceivedAcks,
             cCdmaSoRpUpdHandoffAcceptedReqs,
             cCdmaSoRpUpdHandoffDeniedReqs,
             cCdmaSoRpUpdHandoffDiscardedAcks,
             cCdmaSoRpUpdHandoffInitTxdReqs,
             cCdmaSoRpUpdHandoffReTxdReqs,
             cCdmaSoRpUpdHandoffReaUnSpecFails,
             cCdmaSoRpUpdHandoffAdmProhibFails,
             cCdmaSoRpUpdHandoffMNAuthenFails,
             cCdmaSoRpUpdHandoffIdMismatchFails,
             cCdmaSoRpUpdHandoffBadReqFails,

             cCdmaPcfSoRpSessUpdTxdReqs,
             cCdmaPcfSoRpSessUpdAcptdReqs,
             cCdmaPcfSoRpSessUpdDeniedReqs,
             cCdmaPcfSoRpSessUpdNotAckedReqs,
             cCdmaPcfSoRpSessUpdInitTxdReqs,
             cCdmaPcfSoRpSessUpdReTxdReqs,
             cCdmaPcfSoRpSessUpdRcvdAcks,
             cCdmaPcfSoRpSessUpdDiscardedAcks,
             cCdmaPcfSoRpSessUpdAlwaysOn,
             cCdmaPcfSoRpSessUpdRNPDIT,
             cCdmaPcfSoRpSessUpdParamNotUpdated,
             cCdmaPcfSoRpSessUpdReaUnSpecFails,
             cCdmaPcfSoRpSessUpdMNAuthFails,
             cCdmaPcfSoRpSessUpdIdMismatFails,
             cCdmaPcfSoRpSessUpdBadReqFails
         }
         STATUS current
         DESCRIPTION
                 "A collection of RP registration statistics 
                  MIB objects added in R3.0 to supplement
                  cCdmaPdsnPcfSoRpRegGroup objects."
         ::= { cCdmaPdsnMIBGroups 14 }
         
END
