-- *****************************************************************
-- CISCO-UDLDP-MIB.my
--
-- Nov. 1998, Padma Pullela
--
--
-- Copyright (c) 1998, 2000, 2002, 2003 by cisco Systems, Inc.
-- All rights reserved.
-- *****************************************************************
--

CISCO-UDLDP-MIB DEFINITIONS ::= BEGIN

IMPORTS
        MODULE-IDENTITY, OBJECT-TYPE    
               FROM SNMPv2-SMI                 
        TruthValue
               FROM SNMPv2-TC
        MODULE-COMPLIANCE, OBJECT-GROUP  
               FROM SNMPv2-CONF
        ifIndex
               FROM IF-MIB
        ciscoMgmt                        
                FROM CISCO-SMI;

ciscoUdldpMIB MODULE-IDENTITY
        LAST-UPDATED        "200302210000Z"
        ORGANIZATION        "Cisco Systems, Inc."
        CONTACT-INFO
                "       Cisco Systems
                        Customer Service

                Postal: 170 W Tasman Drive
                        San Jose, CA  95134
                        USA

                   Tel: +1 800 553-NETS

                E-mail: cs-wbu@cisco.com"

        DESCRIPTION
                  "Cisco Uni Direction Link Detection Protocol
                   MIB"

        REVISION    "200302210000Z" 
        DESCRIPTION 
                    "Changed enumerated integer labels in the 
                     cudldpInterfaceOperStatus object from 
                     'bidirectional' to 'biDirectional' and 
                     'notapplicable' to 'notApplicable'."

        REVISION    "200210100000Z" 
        DESCRIPTION
                    "Added cudldpGlobalMode, cudldpInterfaceAdminMode
                     and cudldpInterfaceOperMode objects. 
                     Removed default values for 
                     cudldpGlobalEnable, cudldpHelloInterval
                     and udldpInterfaceEnable. Deprecated 
                     cudldpGlobalEnable and cudldpInterfaceEnable
                     cudldpInterfaceAggressiveMode objects."


        REVISION    "200004100000Z" 
        DESCRIPTION
                    "Added two UDLDP AggressiveMode objects"

        REVISION    "9811100000Z" 
        DESCRIPTION
                "Initial version of this MIB module."
        ::= { ciscoMgmt 118 }


ciscoUdldpMIBObjects OBJECT IDENTIFIER ::=  { ciscoUdldpMIB 1 }

cudldpGlobal         OBJECT IDENTIFIER ::=  { ciscoUdldpMIBObjects 1 }
cudldpInterface      OBJECT IDENTIFIER ::=  { ciscoUdldpMIBObjects 2 }



-- cudldpGlobal

cudldpGlobalEnable OBJECT-TYPE
     SYNTAX      TruthValue 
     MAX-ACCESS  read-write
     STATUS      deprecated
     DESCRIPTION
                    "This variable is used to 
                     enable(true)/disable(false) Uni Direction 
                     Link Detection Protocol on the device. 
                     cudldpGlobalEnable is deprecated  and
                     replaced with cudldpGlobalMode."
        ::= { cudldpGlobal 1 }

cudldpHelloInterval OBJECT-TYPE
        SYNTAX      INTEGER  (7..90)
        UNITS       "seconds"
        MAX-ACCESS  read-write
        STATUS      current
        DESCRIPTION
                    "Indicates interval in seconds at which each port
                     sends a hello packet to all of its neighbors at
                     steady state when the link has been identified as
                     bidirectional."
        ::= { cudldpGlobal 2 }

cudldpGlobalMode OBJECT-TYPE
     SYNTAX      INTEGER {
                          enable(1),
                          disable(2),
                          aggressive(3)
                 } 
     MAX-ACCESS  read-write
     STATUS      current
     DESCRIPTION
                "Indicates the mode of UDLDP feature on the device.
                 enable -- Uni Direction Link Detection Protocol is 
                           enabled on the device.

                 disable -- Uni Directional Link Detection Protocol is
                            disabled on the device.

                 aggresive -- Uni Directional Link Detection protocol
                              is enabled in aggressive mode on the
                              device."
        ::= { cudldpGlobal 3 }


-- cudldpInterface

cudldpInterfaceTable OBJECT-TYPE
        SYNTAX      SEQUENCE OF CudldpInterfaceEntry
        MAX-ACCESS  not-accessible
        STATUS      current
        DESCRIPTION
                "The (conceptual) table containing the status 
                 of UDLDP on the device's interfaces."
        ::= { cudldpInterface 1 }

cudldpInterfaceEntry OBJECT-TYPE
        SYNTAX      CudldpInterfaceEntry
        MAX-ACCESS  not-accessible
        STATUS      current
        DESCRIPTION
                  "A conceptual row of cudldpInterfaceTable. An 
                   entry exists for each interface that supports 
                   UDLDP."
        INDEX { ifIndex }
        ::= { cudldpInterfaceTable 1 }

CudldpInterfaceEntry ::= SEQUENCE {
      cudldpInterfaceEnable         TruthValue,
      cudldpInterfaceOperStatus     INTEGER,
      cudldpInterfaceAggressiveMode TruthValue,
      cudldpInterfaceAdminMode      INTEGER,
      cudldpInterfaceOperMode       INTEGER
}
cudldpInterfaceEnable  OBJECT-TYPE
        SYNTAX        TruthValue
        MAX-ACCESS    read-write
        STATUS        deprecated
        DESCRIPTION
                "This variable is used to enable UDLDP on this 
                 interface.  If cudldpGlobalEnable is set to 
                 'false' then this variable has no effect.
                  cudldpInterfaceEnable is deprecated  and
                  replaced with cudldpInterfaceAdminMode."
        ::= { cudldpInterfaceEntry 1}


cudldpInterfaceOperStatus OBJECT-TYPE
        SYNTAX        INTEGER {
                                shutdown(1), 
                                indeterminant(2),
                                biDirectional(3), 
                                notApplicable(4)
                              }
        MAX-ACCESS    read-only
        STATUS        current
        DESCRIPTION
               " This mib oject contains the following values,
                 which has the meaning as:
                 'shutdown'       - An Uni-Direction link  has been 
                                    detected and the port has been 
                                       disabled.
                 'indeterminant' - Uni-Direction Link Detection  
                                   protocol has not collected enough
                                   information to determine if the 
                                   link is bi directional or not.
                 'biDirectional' - A bi directional link has been 
                                    detected.
                 'notApplicable' - Uni-Direction Link Detection 
                                   Protocol is disabled. 
                "
        ::= { cudldpInterfaceEntry 2}

cudldpInterfaceAggressiveMode OBJECT-TYPE
        SYNTAX        TruthValue 
        MAX-ACCESS    read-write
        STATUS        deprecated
        DESCRIPTION
                  "An indication of whether the UDLDP aggressive mode 
                   is enabled on this interface. If the 
                   aggressive mode is set to 'true', an active port may 
                   be shutdown in case of the abrupt loss of its 
                   neighbor(s) because the loss of communication
                   (heartbeat) with the neighbor(s) is assumed to be
                   caused by a fault; thus, the cudldpInterfaceOperStatus
                   of the active port will be 'shutdown'. Instead, when
                   the aggressive mode is set to 'false', and if there
                   is a loss of communication with the neighbor(s), then
                   the cudldpInterfaceOperStatus of the active port
                   will be 'indeterminant'. 
                   Therefore, this mode is recommended 
                   only for links that don't use hubs, media converters 
                   or similar devices, and where the unexpected loss of 
                   the port's neighbor is not an admissible condition.
                   cudldpInterfaceAggressiveMode is deprecated  and
                   replaced with cudldpInterfaceAdminMode."
        ::= { cudldpInterfaceEntry 3}

cudldpInterfaceAdminMode  OBJECT-TYPE
        SYNTAX        INTEGER {
                          enable(1),
                          disable(2),
                          aggressive(3),
                          default(4)
                      }
        MAX-ACCESS    read-write
        STATUS        current
        DESCRIPTION
                "Indicates the Administartive mode of Uni Direction 
                 Link Detection Protocol Feature configured on this 
                 interface.
                 
                 enable -- Uni Direction Link Detection Protocol is 
                           enabled on this interface.

                 disable -- Uni Direction Link Detection Protocol is
                            disabled on this interface.

                 aggressive -- Uni Direction Link Detection protocol
                              is enabled in aggressive mode on this
                              interface.

                 default -- Whether the Uni Directiona Link Detection 
                            protocol is enabled or not on this interface
                            depends on the object value of 
                            cudldpGlobalMode."
        ::= { cudldpInterfaceEntry 4}

cudldpInterfaceOperMode  OBJECT-TYPE
        SYNTAX        INTEGER {
                          enable(1),
                          disable(2),
                          aggressive(3)
                       }
        MAX-ACCESS read-only
        STATUS     current
        DESCRIPTION
                "Indicates the operational mode of Uni Direction Link 
                 Detection Protocol Feature on this interface."
        ::= { cudldpInterfaceEntry 5}


-- Conformance

ciscoUdldpMIBConformance OBJECT IDENTIFIER ::= { ciscoUdldpMIB 3 }

ciscoUdldpMIBCompliances OBJECT IDENTIFIER 
                                 ::= { ciscoUdldpMIBConformance 1 }

ciscoUdldpMIBGroups OBJECT IDENTIFIER ::= { ciscoUdldpMIBConformance 2 }

-- compliance statements

ciscoUdldpMIBCompliance MODULE-COMPLIANCE
        STATUS  deprecated
        DESCRIPTION
                "The compliance statement for the CISCO-UDLDP-MIB."
        MODULE  -- this module
        MANDATORY-GROUPS { ciscoUdldpMIBGroup }

        ::= { ciscoUdldpMIBCompliances 1 }

ciscoUdldpMIBComplianceRev1 MODULE-COMPLIANCE
        STATUS  deprecated
        DESCRIPTION
                "The compliance statement for the CISCO-UDLDP-MIB."
        MODULE  -- this module
        MANDATORY-GROUPS { ciscoUdldpMIBGroup  }
 
        GROUP        ciscoUdldpAggreModeOptionalGroup
        DESCRIPTION
                "This group is mandatory if the managed system 
                 supports UDLDP aggressive mode feature."

        ::= { ciscoUdldpMIBCompliances 2 }

ciscoUdldpMIBComplianceRev2 MODULE-COMPLIANCE
        STATUS  current
        DESCRIPTION
                "The compliance statement for the CISCO-UDLDP-MIB."
        MODULE  -- this module
        MANDATORY-GROUPS { ciscoUdldpMIBGroup2  }
   
        OBJECT  cudldpGlobalMode
        SYNTAX INTEGER { enable(1), disable(2) }
        DESCRIPTION
              "The support of the value 'aggressive' is not 
               required if the global aggressive mode feature is 
               not supported on the device."

        OBJECT  cudldpInterfaceAdminMode
        SYNTAX INTEGER { enable(1), disable(2) }
        DESCRIPTION
              "The support of the values 'aggressive' and/or 
               'default' is not required if the per interface 
               'aggressive' and/or 'default' mode feature
               is not supported on the device."

        ::= { ciscoUdldpMIBCompliances 3 }

-- Units of Conformance

ciscoUdldpMIBGroup OBJECT-GROUP
      OBJECTS {
               cudldpGlobalEnable,
               cudldpInterfaceEnable,
               cudldpInterfaceOperStatus
              }
      STATUS  deprecated
      DESCRIPTION
              "A collection of objects for use with the  Uni Direction 
               Link Detection Protocol."
        ::= { ciscoUdldpMIBGroups 1 }

ciscoUdldpAggreModeOptionalGroup OBJECT-GROUP
      OBJECTS {
               cudldpInterfaceAggressiveMode,
               cudldpHelloInterval
              }
      STATUS  deprecated
      DESCRIPTION
              " A collection of optional objects providing UDLDP 
                aggressive mode configuration information." 
        ::= { ciscoUdldpMIBGroups 2 }

ciscoUdldpMIBGroup2 OBJECT-GROUP
      OBJECTS {
               cudldpGlobalMode,
               cudldpInterfaceAdminMode,
               cudldpInterfaceOperMode,
               cudldpHelloInterval,
               cudldpInterfaceOperStatus
              }
      STATUS  current
      DESCRIPTION
              "A collection of objects providing Uni Direction
               Link Detection Protocol information."
        ::= { ciscoUdldpMIBGroups 3 }
END
