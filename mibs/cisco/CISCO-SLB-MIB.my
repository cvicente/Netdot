-- *****************************************************************
-- CISCO-SLB-MIB: Mib for SLB entities
--
-- December 1999, Jason Cox
--
-- Copyright (c) 1999, 2002, 2004, 2006 by cisco Systems, Inc.
-- All rights reserved.
-- *****************************************************************
--
CISCO-SLB-MIB DEFINITIONS ::= BEGIN

IMPORTS
        MODULE-IDENTITY,
        NOTIFICATION-TYPE,
        OBJECT-TYPE,
        IpAddress,
        Unsigned32,
        Counter32,
        Counter64,
        Gauge32
                FROM SNMPv2-SMI

        CiscoPort,
        CiscoIpProtocol
                FROM CISCO-TC

        TimeInterval,
        TruthValue,
        DateAndTime,
        TEXTUAL-CONVENTION,
        RowStatus,
        StorageType
                FROM SNMPv2-TC

        MODULE-COMPLIANCE,
        OBJECT-GROUP,
        NOTIFICATION-GROUP
                FROM SNMPv2-CONF

        InetAddressType,
        InetAddress,
        InetPortNumber,
        InetAddressPrefixLength
                FROM INET-ADDRESS-MIB

        SnmpAdminString
                FROM SNMP-FRAMEWORK-MIB

        ciscoMgmt
                FROM CISCO-SMI;

ciscoSlbMIB MODULE-IDENTITY
        LAST-UPDATED    "200601130000Z"
        ORGANIZATION    "Cisco Systems, Inc."
        CONTACT-INFO
                "       Cisco Systems
                        Customer Service

                Postal: 170 W. Tasman Drive
                        San Jose, CA  95134
                        USA

                   Tel: +1 800 553-NETS

                E-mail: cs-slb@cisco.com"
        DESCRIPTION
                "The MIB for managing Server Load Balancing Manager(s),
                such as the Cisco IOS SLB product. 

                This MIB includes instrumentation for the manager-side
                implementation of the Dynamic Feedback Protocol (DFP).
                A DFP uses the DFP protocol to communicate with
                DFP agents in order to obtain information about
                Servers.

                This MIB includes the objects required for implementing
                the load balancer management side of the
                Server/Application State Protocol (SASP).  The load
                balancer is responsible for registering Members with a
                SASP-Agent.  A Member is an entity that is defined on
                the load balancer to service Internet traffic.  The
                responsibility of the Agent is to monitor the Members,
                and report a recommended weight to the load balancer.
                The weight is then used in load balancing decisions.

                Acronyms and terms:
                
                  DFP    Dynamic Feedback Protocol
                  SASP   Server to Application State Protocol
                  GGSN   Gateway GPRS Support Node
                  GPRS   General Packet Radio Service
                  GTP    GPRS Tunneling Protocol
                  SASP   Server/Application State Protocol
                  SGSN   Serving GPRS Support Node
                "
        REVISION        "200601130000Z"
        DESCRIPTION
                "- Added following enums to SlbPredictor TC
                   leastLoaded
                   httpCookieHash
                   httpHeaderHash.

                - Increased the range for SlbServerString TC
                  from 1..15 to 1..96.

                - Added following Tables:
                  slbVServerInfoTable
                  slbVServerIPTable

                - Added following Notifications:
                  ciscoSlbVServerStateChange
                  ciscoSlbVServerVIPStateChange

                - Added cSlbVServerStateChangeNotifEnabled object

                - Added following in Compliance/Conformance
                  ciscoSlbMIBComplianceRev3."

        REVISION        "200503310000Z"
        DESCRIPTION
                "Extending MIB to support the Server/Application State
                Protocol (SASP).  The following tables were added to
                the MIB:
                 - slbSaspTable
                 - slbSaspAgentTable,
                 - slbSaspGroupTable,
                 - slbSaspMemberTable
                 - slbSaspStatsTable"
        REVISION        "200203180000Z"
        DESCRIPTION
                "Defining more server states and predictor options for
                 Content Switching Module (CSM) product."
        REVISION        "200201151500Z"
        DESCRIPTION
                "Extending MIB to support GTP service.  Updated
                SlbRealServerState and SlbVirtualServState with
                more states."
        REVISION        "200010200000Z"
        DESCRIPTION
                "Extending MIB to support VirtualMask and
                 service wsp."
        REVISION        "200005080000Z"
        DESCRIPTION
                "Initial version of this MIB module."
        ::= { ciscoMgmt 161 }

ciscoSlbMIBObjects      OBJECT IDENTIFIER ::= { ciscoSlbMIB 1 }
slbStats                OBJECT IDENTIFIER ::= { ciscoSlbMIBObjects 1 }
slbServerFarms          OBJECT IDENTIFIER ::= { ciscoSlbMIBObjects 2 }
slbRealServers          OBJECT IDENTIFIER ::= { ciscoSlbMIBObjects 3 }
slbVirtualServers       OBJECT IDENTIFIER ::= { ciscoSlbMIBObjects 4 }
slbConnections          OBJECT IDENTIFIER ::= { ciscoSlbMIBObjects 5 }
slbVirtualClients       OBJECT IDENTIFIER ::= { ciscoSlbMIBObjects 6 }
slbStickyObjects        OBJECT IDENTIFIER ::= { ciscoSlbMIBObjects 7 }
slbNotificationObjects  OBJECT IDENTIFIER ::= { ciscoSlbMIBObjects 8 }
slbDfpPassword          OBJECT IDENTIFIER ::= { ciscoSlbMIBObjects 9 }
slbDfpAgents            OBJECT IDENTIFIER ::= { ciscoSlbMIBObjects 10 }
slbDfpReal              OBJECT IDENTIFIER ::= { ciscoSlbMIBObjects 11 }
slbSasp                 OBJECT IDENTIFIER ::= { ciscoSlbMIBObjects 12 }
slbSaspAgents           OBJECT IDENTIFIER ::= { ciscoSlbMIBObjects 13 }
slbSaspGroups           OBJECT IDENTIFIER ::= { ciscoSlbMIBObjects 14 }
slbSaspMembers          OBJECT IDENTIFIER ::= { ciscoSlbMIBObjects 15 }
slbSaspStats            OBJECT IDENTIFIER ::= { ciscoSlbMIBObjects 16 }

--  ********************************************************************
--  *                                                                  *
--  * Textual Conventions                                              *
--  *                                                                  *
--  ********************************************************************

SlbServerString ::= TEXTUAL-CONVENTION
        STATUS          current
        DESCRIPTION
                "The configured name associated with an SLB object."
        SYNTAX OCTET STRING (SIZE (1..96))

SlbPasswordString ::= TEXTUAL-CONVENTION
        STATUS          current
        DESCRIPTION
                "The string for the Dynamic Feedback Protocol (DFP)
                password.  A zero-length value when writing this object
                will unset the password."
        SYNTAX OCTET STRING (SIZE (0..32))

SlbConnectionState ::= TEXTUAL-CONVENTION
        STATUS          current
        DESCRIPTION
                "The state for TCP, UDP, and WSP connections being
                load-balanced by the SLB feature.  Each protocol uses a 
                subset of these states.
                'init'     : Connection has seen traffic and is in the
                             process of being load-balanced.
                'synClient': SLB has seen a client SYN for this
                             connection.
                'synServer': SLB has seen a server SYN for this
                             connection.
                'synBoth'  : SLB has seen both client and server SYNs
                             for this connection.
                'estab'    : Connection is established.
                'finClient': SLB has seen a client FIN for this
                             connection.
                'finServer': SLB has seen a server FIN for this
                             connection.
                'closing'  : Connection is in the process of coming
                             down.
                'zombie'   : Connection exists but is not in use,
                             waiting for timers to expire.
                'conclient': Session has seen a connection request from 
                             client.
                'conserver': Session has seen a connection request from 
                             server."
        SYNTAX INTEGER {
                init(1),
                synClient(2),
                synServer(3),
                synBoth(4),
                estab(5),
                finClient(6),
                finServer(7),
                closing(8),
                zombie(9),
                conclient(10),
                conserver(11)
        }

SlbPredictor ::= TEXTUAL-CONVENTION
        STATUS          current
        DESCRIPTION
                "The predictor represents the load-balancing algorithm
                being used on a server farm to distribute load evenly
                among real servers. 
                'roundRobin'  : assign evenly amongst real servers.
                'leastConns'  : assign to the real server with the least
                                number of current connections.
                'ipHash'      : assign based on the hash value of the
                                source IP and destination IP address.
                'ipHashSrc'   : assign based on the hash value of the
                                source IP address.
                'ipHashDest'  : assign based on the hash value of the
                                destination IP address.
                'urlHash'     : assign based on the hash value of the
                                URL string.
                'forward'     : forward the connection to the
                                appropriate next-hop as determined by
                                a routing lookup on the destination
                                IP address.
                'leastLoaded' : assign to a real server that is
                                least loaded/busy.  The load
                                information is available from
                                agents(DFP, SASP etc).
                'httpCookieHash' : assign based on the hash value of
                                   the HTTP Cookie value.
                'httpHeaderHash' : assign based on the hash value of
                                   the HTTP Header Name."
        SYNTAX INTEGER {
                roundRobin     (1),
                leastConns     (2),
                ipHash         (3),
                ipHashSrc      (4),
                ipHashDest     (5),
                urlHash        (6),
                forward        (7),
                leastLoaded    (8),
                httpCookieHash (9),
                httpHeaderHash (10)
        }

SlbRealServerState ::= TEXTUAL-CONVENTION
        STATUS          current
        DESCRIPTION
                "The server state represents the state of a real server
                being load-balanced by SLB.
                'outOfService'     : Server is not in use by SLB as a
                                     destination for client
                                     connections.  This state can be
                                     written and read.
                'inService'        : Server is in use as a destination
                                     for SLB client connections.  This
                                     state can be written and read.
                'failed'           : Server has failed and will not be
                                     retried for retry timer seconds.
                                     This state can only be read.
                'readyToTest'      : Server has failed and has an
                                     expired retry timer, test
                                     connections will begin flow to
                                     it soon. This state can only be
                                     read.
                'testing'          : Server has failed and been given
                                     another test connection, success
                                     of this connection is not known
                                     yet.  This state can only be read.
                'maxConnsThrottle' : Server has reached its maximum
                                     number of connections and is no
                                     longer being given connections.
                                     This state can only be read.
                'maxClientsThrottle': Server has reached the maximum
                                      allowed clients.  This state
                                      can only be read.
                'dfpThrottle'      : DFP has lowered the weight of 
                                     this server to throttle level, so
                                     that no new connections will be 
                                     assigned to it until DFP raises
                                     its weight. 
                                     This state can only be read.
                'probeFailed'      : SLB probe to this this server has
                                     failed.  No new connections will be
                                     assigned to it until a probe to 
                                     this server succeeds.  This state 
                                     can only be read.
                'probeTesting'     : Server has received a test probe
                                     from SLB.  This state can only 
                                     be read.
                'operWait'         : Server is ready to go operational,
                                     but is waiting for the associated
                                     redirect virtual to be inservice.
                                     This state can only be read.
                'testWait'         : Server is ready to be tested. This
                                     state is applicable only when the
                                     server is used for http redirect
                                     load balancing. This state can
                                     only be read.
                'inbandProbeFailed': Server has failed the inband
                                     Health Probe agent.  This state
                                     can only be read.
                'returnCodeFailed' : Server has been disabled because
                                     it returned an HTTP code that
                                     matched a configured value.
                                     This state can only be read."

        SYNTAX INTEGER {
                outOfService(1),
                inService(2),
                failed(3),
                readyToTest(4),
                testing(5),
                maxConnsThrottle(6),
                maxClientsThrottle(7),
                dfpThrottle(8),
                probeFailed(9),
                probeTesting(10),
                operWait(11),
                testWait(12),
                inbandProbeFailed(13),
                returnCodeFailed(14)
        }

SlbVirtualServState ::= TEXTUAL-CONVENTION
        STATUS          current
        DESCRIPTION
                "The state of SLB virtual server
                'outOfService' : Virtual server is not active and is
                                 not affecting client traffic in any
                                 way.
                'inService'    : Virtual server is active and is
                                 load-balancing matching client traffic
                                 to available real servers.
                'standby'      : Virtual server is a backup for a
                                 virtual server on another SLB device,
                                 and is currently inactive.
                'inOperReal'   : Real server associated with this
                                 redirect virtual server is not
                                 operational.  This state can only 
                                 be read.
                'stbInOperReal': Real server associated with this 
                                 redirect virtual server is not
                                 operational, and this virtual server
                                 is in standby state.  This state 
                                 can only be read.
                'testReal'     : This is a redirect virtual server and
                                 the real server associated with it is 
                                 being tested.  This state can only 
                                 be read.
                'outOfMemory'  : Virtual server is not enabled because
                                 it does not have enough memory to
                                 hold the configured matching policy
                                 information.  This state can only be
                                 read."
        SYNTAX INTEGER {
                outOfService(1),
                inService(2),
                standby(3),
                inOperReal(4),
                stbInOperReal(5),
                testReal(6),
                outOfMemory(7)
        }

SlbVirtualService ::= TEXTUAL-CONVENTION
        STATUS          current
        DESCRIPTION
                "The special service configured for this virtual server.
                Such a specification ensures that session(s) for a given
                protocol are tracked and assigned to the same real 
                machine.  These services include:
                'ftp' : File Transfer Protocol
                'wsp' : Wireless Session Protocol
                'gtp' : GPRS Tunnelling Protocol
                'rtsp': Real-Time Streaming Protocol"
        SYNTAX INTEGER {
                none(1),
                ftp(2),
                wsp(3),
                gtp(4),
                rtsp(5)
        }

SlbDfpAgentState ::= TEXTUAL-CONVENTION
        STATUS          current
        DESCRIPTION
                "The status of a remote Dynamic Feedback Protocol (DFP)
                agent as it appears to a local DFP manager.
                'notOpen'       : The initial state when the DFP Agent
                                  block is instantiated.
                'trying'        : The state when the Agent tries to
                                  open the socket to the DFP manger.
                'connecting'    : The state when the Agent opens the
                                  socket, and is connecting to the
                                  DFP manager.
                'open'          : The state when an Agent is talking to
                                  the DFP manager. This is the desirable
                                  place to be.
                'failed'        : The state when there is an error in
                                  the data, or when the maximum number
                                  of retries is reached.
                'securityError' : The state when there is a security
                                  error in the received message. Either
                                  there is no security vector when one
                                  was required, or the MD5 string in
                                  the message did not match the
                                  expected result (password not
                                  correct)."
        SYNTAX INTEGER {
                notOpen(1),
                trying(2),
                connecting(3),
                open(4),
                failed(5),
                securityError(6)
        }

SlbSaspLBHealth ::= TEXTUAL-CONVENTION
        STATUS          current
        DESCRIPTION
                "The Load Balancer Health that is reported to the SASP
                Agent in the Set Load Balancer State Message.  This
                value represents the load balancers ability to handle
                SASP messages.

                'other'          : The load balancer health when none
                                   of the other values apply.
                'idle'           : SASP is enabled on the load balancer,
                                   but no SASP Agents or Members are
                                   configured.
                'down'           : The load balancer cannot handle any
                                   SASP messages at this time.
                'saturated'      : The load balancer is failing to
                                   process SASP messages in a timely
                                   manner, and messages are being lost.
                'overUsed'       : The load balancer is failing to
                                   process SASP messages in a timely
                                   manner.
                'msgLimitReached': The load balancer has reached it
                                   functional limit in its ability to
                                   handle SASP messages.  Additional
                                   work should be avoided.
                'heavyLoad'      : A plethora of SASP messages are sent
                                   and received for a modest to large
                                   number of SASP Agents and Members.
                'moderateLoad'   : SASP messages are sent on a regular
                                   basis for a small to modest number
                                   of SASP Agents and Members.
                'lightLoad'      : SASP messages are sent and received
                                   on a consistent basis, over a long
                                   period of time, for a small number
                                   of SASP Agents and Members.
                'healthy'        : SASP messages are sporadically being
                                   sent and received by the load
                                   balancer for a small number of SASP
                                   Agents and Members."
        SYNTAX INTEGER {
                other(1),
                idle(2),
                down(3),
                saturated(4),
                overUsed(5),
                msgLimitReached(6),
                heavyLoad(7),
                moderateLoad(8),
                lightLoad(9),
                healthy(10)
        }

SlbSaspRedundancy ::= TEXTUAL-CONVENTION
        STATUS          current
        DESCRIPTION
                "The redundancy state of the Load Balancer.
                'other'          : The redundant state of the Load
                                   Balancer when none of the other
                                   states apply.
                'master'         : The redundant state of the Load
                                   Balancer if it is not in a redundant
                                   setup, or is the active system used
                                   in a redundant setup.
                'backup'         : The redundant state of the Load
                                   Balancer if it is the idle system in
                                   a redundant setup."
        SYNTAX INTEGER {
                other(1),
                master(2),
                backup(3)
        }

SlbSaspAgentState ::= TEXTUAL-CONVENTION
        STATUS          current
        DESCRIPTION
                "The status of a remote Server Application State
                Protocol (SASP) Agent as it appears to a local SASP
                manager.
                'other'         : The state the Agent enters when none
                                  of the other states apply. 
                'initialized'   : The initial state when the SASP Agent
                                  memory is created.
                'closed'        : The state the SASP Agent enters when
                                  the SASP functionality is disabled,
                                  but the Agent has not been removed.
                'trying'        : The state when the Agent tries to
                                  open the socket to the SASP manger.
                'connecting'    : The state when the SASP Manager opens
                                  the socket, and is connecting to the
                                  SASP Agent.
                'established'   : The state when an Agent is
                                  communicating with the SASP manager.
                                  This is the desirable place to be.
                'downTrying'    : The state when there is a
                                  communication failure with the SASP
                                  Agent, and the load balancer is
                                  attempting to reconnect to the Agent.
                'downDuplicate' : The Agent enters this state if a 
                                  duplicate load balancer identifier is
                                  detected on the network.
                'down'          : The state of the Agent when there is a
                                  communication failure, and the load
                                  balancer is unable to re-establish the
                                  connection."
        SYNTAX INTEGER {
                other(1),
                initialized(2),
                closed(3),
                trying(4),
                connecting(5),
                established(6),
                downTrying(7),
                downDuplicate(8),
                down(9)
        }

SlbNatSetting ::= TEXTUAL-CONVENTION
        STATUS          current
        DESCRIPTION
                "The current network address translation (NAT) setting
                for a server farm.
                'noNat'             : The server farm is not configured
                                      for NAT.
                'clientNat'         : The server farm is configured to
                                      translate client IP addresses.
                'serverNat'         : The server farm is configured to
                                      translate server IP addresses.
                'clientAndServerNat': The server farm is configured to
                                      translate client and server IP
                                      addresses."

        SYNTAX INTEGER {
                noNat(1),
                clientNat(2),
                serverNat(3),
                clientAndServerNat(4)
        }

--  *************************************************************
--  *                                                           *
--  * SLB - Statistics Table                                    *
--  *                                                           *
--  *************************************************************

slbStatsTable                           OBJECT-TYPE
        SYNTAX          SEQUENCE OF SlbStatsTableEntry
        MAX-ACCESS      not-accessible
        STATUS          current
        DESCRIPTION
                "A table of SLB statistics for all local SLB entities."
        ::= { slbStats 1 }

slbStatsTableEntry                      OBJECT-TYPE
        SYNTAX          SlbStatsTableEntry
        MAX-ACCESS      not-accessible
        STATUS          current
        DESCRIPTION
                "A list of SLB statistics for a particular SLB entity."
        INDEX   {
                slbEntity
        }
        ::= { slbStatsTable 1 }

SlbStatsTableEntry ::= SEQUENCE {
        slbEntity                               Unsigned32,
        slbStatsUnassistedSwitchingPkts         Counter32,
        slbStatsUnassistedSwitchingHCPks        Counter64,
        slbStatsAssistedSwitchingPkts           Counter32,
        slbStatsAssistedSwitchingHCPkts         Counter64,
        slbStatsCreatedConnections              Counter32,
        slbStatsCreatedHCConnections            Counter64,
        slbStatsEstablishedConnections          Counter32,
        slbStatsEstablishedHCConnections        Counter64,
        slbStatsDestroyedConnections            Counter32,
        slbStatsDestroyedHCConnections          Counter64,
        slbStatsReassignedConnections           Counter32,
        slbStatsReassignedHCConnections         Counter64,
        slbStatsZombies                         Counter32,
        slbStatsHCZombies                       Counter64
}

slbEntity                               OBJECT-TYPE
        SYNTAX          Unsigned32
        MAX-ACCESS      not-accessible
        STATUS          current
        DESCRIPTION
                "The SLB instance reference number for this server.
                This allows multiple SLB's to exist on the same SNMP
                system.  This object's value generally corresponds to 
                the slot number where the module resides."
        ::= { slbStatsTableEntry 1 }

slbStatsUnassistedSwitchingPkts         OBJECT-TYPE
        SYNTAX          Counter32
        UNITS           "packets"
        MAX-ACCESS      read-only
        STATUS          current
        DESCRIPTION
                "The number of packets forwarded by the Software Load
                Balancing manager's software."
        ::= { slbStatsTableEntry 2 }

slbStatsUnassistedSwitchingHCPks        OBJECT-TYPE
        SYNTAX          Counter64
        UNITS           "packets"
        MAX-ACCESS      read-only
        STATUS          current
        DESCRIPTION
                "The number of packets forwarded by the Software Load
                Balancing manager's software.  This is the 64-bit
                version of slbStatsUnassistedPkts."
        ::= { slbStatsTableEntry 3 }

slbStatsAssistedSwitchingPkts           OBJECT-TYPE
        SYNTAX          Counter32
        UNITS           "packets"
        MAX-ACCESS      read-only
        STATUS          current
        DESCRIPTION
                "The number of packets handled by SLB which were
                switched via the highest-performance switching path."
        ::= { slbStatsTableEntry 4 }

slbStatsAssistedSwitchingHCPkts         OBJECT-TYPE
        SYNTAX          Counter64
        UNITS           "packets"
        MAX-ACCESS      read-only
        STATUS          current
        DESCRIPTION
                "The number of packets handled by SLB which were
                switched via the highest-performance switching path.
                This is the 64-bit version of
                slbStatsAssistedSwitchingPkts."
        ::= { slbStatsTableEntry 5 }

slbStatsCreatedConnections              OBJECT-TYPE
        SYNTAX          Counter32
        UNITS           "connections"
        MAX-ACCESS      read-only
        STATUS          current
        DESCRIPTION
                "The number of TCP and UDP connections created since
                SLB was configured.  TCP connections are created
                after seeing a SYN for a connection.  UDP connections
                are created based on the source and destination and
                are removed based on a timer."
        ::= { slbStatsTableEntry 6 }

slbStatsCreatedHCConnections            OBJECT-TYPE
        SYNTAX          Counter64
        UNITS           "connections"
        MAX-ACCESS      read-only
        STATUS          current
        DESCRIPTION
                "The number of connections created by SLB since it was
                configured.  TCP connections are created after seeing a
                SYN for a connection.  UDP connections are created
                based on the source and destination and are removed
                based on a timer.  This is the 64-bit version of
                slbStatsCreatedConnections."
        ::= { slbStatsTableEntry 7 }

slbStatsEstablishedConnections          OBJECT-TYPE
        SYNTAX          Counter32
        UNITS           "connections"
        MAX-ACCESS      read-only
        STATUS          current
        DESCRIPTION
                "The number of connections established through SLB
                (reached the ESTAB state).  TCP connections reach
                the ESTAB state after a SYN - SYN/ACK exchange.  UDP
                connections reach the ESTAB state after data is sent
                from the client or server."
        ::= { slbStatsTableEntry 8 }

slbStatsEstablishedHCConnections        OBJECT-TYPE
        SYNTAX          Counter64
        UNITS           "connections"
        MAX-ACCESS      read-only
        STATUS          current
        DESCRIPTION
                "The number of connections established through SLB
                (reached the ESTAB state).  TCP connections reach
                the ESTAB state after a SYN - SYN/ACK exchange.  UDP
                connections reach the ESTAB state after data is sent
                from the client or server.  This is the 64-bit version
                of slbStatsEstablisedConnections."
        ::= { slbStatsTableEntry 9 }

slbStatsDestroyedConnections            OBJECT-TYPE
        SYNTAX          Counter32
        UNITS           "connections"
        MAX-ACCESS      read-only
        STATUS          current
        DESCRIPTION
                "The number of TCP and UDP connections destroyed by
                SLB, either by TCPIP teardown or timeout.  UDP
                connections can only be timed out."
        ::= { slbStatsTableEntry 10 }

slbStatsDestroyedHCConnections          OBJECT-TYPE
        SYNTAX          Counter64
        UNITS           "connections"
        MAX-ACCESS      read-only
        STATUS          current
        DESCRIPTION
                "The number of TCP and UDP connections destroyed by SLB,
                either by TCPIP teardown or timeout.  UDP connections
                can only be timed out.  This is the 64-bit version of
                slbStatsDestroyedConnections."
        ::= { slbStatsTableEntry 11 }

slbStatsReassignedConnections           OBJECT-TYPE
        SYNTAX          Counter32
        UNITS           "connections"
        MAX-ACCESS      read-only
        STATUS          current
        DESCRIPTION
                "The number of TCP and UDP connections reassigned from
                one real server to another."
        ::= { slbStatsTableEntry 12 }

slbStatsReassignedHCConnections         OBJECT-TYPE
        SYNTAX          Counter64
        UNITS           "connections"
        MAX-ACCESS      read-only
        STATUS          current
        DESCRIPTION
                "The number of TCP and UDP connections reassigned from
                one real server to another.  This is the 64-bit version
                of slbStatsReassignedConnections."
        ::= { slbStatsTableEntry 13 }

slbStatsZombies                         OBJECT-TYPE
        SYNTAX          Counter32
        UNITS           "zombies"
        MAX-ACCESS      read-only
        STATUS          current
        DESCRIPTION
                "The number of TCP and UDP connections currently in
                the zombie state waiting for timers to expire."
        ::= { slbStatsTableEntry 14 }

slbStatsHCZombies                       OBJECT-TYPE
        SYNTAX          Counter64
        UNITS           "zombies"
        MAX-ACCESS      read-only
        STATUS          current
        DESCRIPTION
                "The number of TCP and UDP connections currently in
                the zombie state waiting for timers to expire.  This
                is the 64-bit version of slbStatsZombies."
        ::= { slbStatsTableEntry 15 }

--  *************************************************************
--  *                                                           *
--  * SLB - Server Farm Table                                   *
--  *                                                           *
--  *************************************************************

slbServerFarmTable                      OBJECT-TYPE
        SYNTAX          SEQUENCE OF SlbServerFarmTableEntry
        MAX-ACCESS      not-accessible
        STATUS          current
        DESCRIPTION
                "This is a table of server farms, each of which is a
                group of real servers to be used by SLB for load
                balancing.  Columnar objects can be modified when the
                row is 'active'.  Rows can be created and destroyed.
                Entries are added to this table via
                slbServerFarmRowStatus in accordance with the
                RowStatus convention."
        ::= { slbServerFarms 1 }

slbServerFarmTableEntry                 OBJECT-TYPE
        SYNTAX          SlbServerFarmTableEntry
        MAX-ACCESS      not-accessible
        STATUS          current
        DESCRIPTION
                "Information about a particular server farm served by
                a particular local SLB entity."
        INDEX   {
                slbEntity,
                slbServerFarmName
        }
        ::= { slbServerFarmTable 1 }

SlbServerFarmTableEntry ::= SEQUENCE {
        slbServerFarmName                       SlbServerString,
        slbServerFarmPredictor                  SlbPredictor,
        slbServerFarmNat                        SlbNatSetting,
        slbServerFarmNumberOfRealServers        Unsigned32,
        slbServerFarmBindId                     Unsigned32,
        slbServerFarmRowStatus                  RowStatus
}

slbServerFarmName                       OBJECT-TYPE
        SYNTAX          SlbServerString
        MAX-ACCESS      not-accessible
        STATUS          current
        DESCRIPTION
                "The name of server farm."
        ::= { slbServerFarmTableEntry 1 }

slbServerFarmPredictor                  OBJECT-TYPE
        SYNTAX          SlbPredictor
        MAX-ACCESS      read-only
        STATUS          current
        DESCRIPTION
                "The load balancing algorithm in use by the server farm
                for its real servers for the local SLB entity."
        DEFVAL          { roundRobin }
        ::= { slbServerFarmTableEntry 2 }

slbServerFarmNat                        OBJECT-TYPE
        SYNTAX          SlbNatSetting
        MAX-ACCESS      read-create
        STATUS          current
        DESCRIPTION
                "The type of NAT employed by the local SLB entity for
                servers in this server farm."
        DEFVAL          { noNat }
        ::= { slbServerFarmTableEntry 3 }

slbServerFarmNumberOfRealServers        OBJECT-TYPE
        SYNTAX          Unsigned32
        MAX-ACCESS      read-create
        STATUS          current
        DESCRIPTION
                "The number of real servers in this server farm."
        DEFVAL          { 0 }
        ::= { slbServerFarmTableEntry 4 }

slbServerFarmBindId                     OBJECT-TYPE
        SYNTAX          Unsigned32
        MAX-ACCESS      read-create
        STATUS          current
        DESCRIPTION
                "slbServerFarmBindId is used to identify one or more
                real servers for which slbDfpRealWeight applies to the
                real server's slbRealOperWeight. The identification
                is done by finding rows in slbServerFarmTable for which
                slbServerFarmBindId matches slbDfpRealBindId. For each
                identified server farm, extract the slbServerFarmName
                and use this value together with slbDfpRealIpAddress
                and slbDfpRealPort to identify the row in
                slbRealTable."
        DEFVAL          { 0 }
        ::= { slbServerFarmTableEntry 5 }

slbServerFarmRowStatus                  OBJECT-TYPE
        SYNTAX          RowStatus
        MAX-ACCESS      read-create
        STATUS          current
        DESCRIPTION
                "The object is used by a management station to create
                or delete the row entry in slbServerFarmTable following
                the RowStatus textual convention."
        ::= { slbServerFarmTableEntry 6 }

--  *************************************************************
--  *                                                           *
--  * SLB - Real Server Table                                   *
--  *                                                           *
--  *************************************************************

slbRealTable                            OBJECT-TYPE
        SYNTAX          SEQUENCE OF SlbRealTableEntry
        MAX-ACCESS      not-accessible
        STATUS          current
        DESCRIPTION
                "A table of real servers.  Columnar objects can be
                modified when the row is 'active'.  Rows can be created
                and destroyed.  Entries are added to this table via
                slbRealRowStatus in accordance with the RowStatus
                convention."
        ::= { slbRealServers 1 }

slbRealTableEntry                       OBJECT-TYPE
        SYNTAX          SlbRealTableEntry
        MAX-ACCESS      not-accessible
        STATUS          current
        DESCRIPTION
                "Information about a particular real server in a
                particular server farm, served by a particular local
                SLB entity.  "
        INDEX   {
                slbEntity,
                slbRealServerFarmName,
                slbRealIpAddress,
                slbRealPort
        }
        ::= { slbRealTable 1 }

SlbRealTableEntry ::= SEQUENCE {
        slbRealServerFarmName                   SlbServerString,
        slbRealIpAddress                        IpAddress,
        slbRealPort                             CiscoPort,
        slbRealState                            SlbRealServerState,
        slbRealNumberOfConnections              Gauge32,
        slbRealNumberOfDummyConnections         Unsigned32,
        slbRealMaxConnections                   Unsigned32,
        slbRealAdminWeight                      Unsigned32,
        slbRealOperWeight                       Gauge32,
        slbRealMetric                           Gauge32,
        slbRealReassign                         Unsigned32,
        slbRealRetryInterval                    TimeInterval,
        slbRealFailedConnections                Unsigned32,
        slbRealFailedClients                    Unsigned32,
        slbRealConsecutiveFails                 Gauge32,
        slbRealTotalFails                       Counter32,
        slbRealRowStatus                        RowStatus,
        slbRealTotalConnections                 Counter32,
        slbRealHCTotalConnections               Counter64
}

slbRealServerFarmName                   OBJECT-TYPE
        SYNTAX          SlbServerString
        MAX-ACCESS      not-accessible
        STATUS          current
        DESCRIPTION
                "The real server's server farm name."
        ::= { slbRealTableEntry 1 }

slbRealIpAddress                        OBJECT-TYPE
        SYNTAX          IpAddress
        MAX-ACCESS      not-accessible
        STATUS          current
        DESCRIPTION
                "The IP address of real server."
        ::= { slbRealTableEntry 2 }

slbRealPort                             OBJECT-TYPE         
        SYNTAX          CiscoPort
        MAX-ACCESS      not-accessible
        STATUS          current
        DESCRIPTION
                "The TCP or UDP port of real server.  This is used if
                SLB NAT is configured (see slbServerFarmNat).  If SLB
                is not using NAT, this value will be 0."
        REFERENCE
                "slbServerFarmNat"
        ::= { slbRealTableEntry 3 }

slbRealState                            OBJECT-TYPE
        SYNTAX          SlbRealServerState
        MAX-ACCESS      read-create
        STATUS          current
        DESCRIPTION
                "The current state of real server."
        DEFVAL          { outOfService }
        ::= { slbRealTableEntry 4 }

slbRealNumberOfConnections              OBJECT-TYPE
        SYNTAX          Gauge32
        MAX-ACCESS      read-only
        STATUS          current
        DESCRIPTION
                "The number TCP and UDP connections currently assigned
                to this real server."
        ::= { slbRealTableEntry 5 }

slbRealNumberOfDummyConnections         OBJECT-TYPE
        SYNTAX          Unsigned32
        MAX-ACCESS      read-only
        STATUS          current
        DESCRIPTION
                "The current number of idle dummy connections that are
                not in use but are reserved for this real server to
                accomplish slow-start."
        ::= { slbRealTableEntry 6 }

slbRealMaxConnections                   OBJECT-TYPE
        SYNTAX          Unsigned32
        MAX-ACCESS      read-create
        STATUS          current
        DESCRIPTION
                "The configured maximum number of concurrent connections
                which SLB will deliver to this real server."
        DEFVAL          { 4294967295 }
        ::= { slbRealTableEntry 7 }

slbRealAdminWeight                      OBJECT-TYPE
        SYNTAX          Unsigned32 ( 0..65535 )
        MAX-ACCESS      read-create
        STATUS          current
        DESCRIPTION
                "The user configured weight of the real server for the
                load-balancing algorithms.  A weight of zero indicates
                that no new connections will be assigned to this real
                server.  Higher weight values indicate to the
                load-balancing algorithms a higher availability of this
                real server to accept more work."
        DEFVAL          { 8 }
        ::= { slbRealTableEntry 8 }

slbRealOperWeight                       OBJECT-TYPE
        SYNTAX          Gauge32
        MAX-ACCESS      read-only
        STATUS          current
        DESCRIPTION
                "The actual operating weight of the real server used
                by the load-balancing algorithms.  This can be adjusted
                dynamically by DFP.  A weight of zero indicates that no
                new connections will be assigned to this real server.
                Higher weight values indicate to the load-balancing
                algorithms a higher availability of this real server to
                accept more work."
        ::= { slbRealTableEntry 9 }

slbRealMetric                           OBJECT-TYPE
        SYNTAX          Gauge32
        MAX-ACCESS      read-only
        STATUS          current
        DESCRIPTION
                "The value used by the least connections load-balancing
                algorithm.  It is the number of connections divided by
                the actual operating weight.  New connections will be
                given to the server with the smaller metric."
        ::= { slbRealTableEntry 10 }

slbRealReassign                         OBJECT-TYPE
        SYNTAX          Unsigned32
        MAX-ACCESS      read-create
        STATUS          current
        DESCRIPTION
                "The number of consecutive TCP SYNs sent to the real
                server with no answer before reassigning the
                connection to another real server."
        DEFVAL          { 3 }
        ::= { slbRealTableEntry 11 }

slbRealRetryInterval                    OBJECT-TYPE
        SYNTAX          TimeInterval
        MAX-ACCESS      read-create
        STATUS          current
        DESCRIPTION
                "The time interval between retries while the server is
                in the Failed state."
        DEFVAL          { 60 }
        ::= { slbRealTableEntry 12 }

slbRealFailedConnections                OBJECT-TYPE
        SYNTAX          Unsigned32
        MAX-ACCESS      read-create
        STATUS          current
        DESCRIPTION
                "The number of failed connections after which the real
                server goes to Failed state.  A failed connection is
                when a SYN timeouts or a RST is received from the
                real server."
        DEFVAL          { 8 }
        ::= { slbRealTableEntry 13 }

slbRealFailedClients                    OBJECT-TYPE
        SYNTAX          Unsigned32
        MAX-ACCESS      read-create
        STATUS          current
        DESCRIPTION
                "The number of connections with distinct client IP
                addresses which need to fail on this real server
                before it goes to Failed state.  A failed connection
                is when a SYN timeouts or a RST is received from the
                real server."
        DEFVAL          { 8 }
        ::= { slbRealTableEntry 14 }

slbRealConsecutiveFails                 OBJECT-TYPE
        SYNTAX          Gauge32
        MAX-ACCESS      read-only
        STATUS          current
        DESCRIPTION
                "The number of connection failures to this real
                server without a successful connection.  A failed
                connection is when a SYN timeouts or a RST is received
                from the real server."
        ::= { slbRealTableEntry 15 }

slbRealTotalFails                       OBJECT-TYPE
        SYNTAX          Counter32
        MAX-ACCESS      read-only
        STATUS          current
        DESCRIPTION
                "The total number of times this real server has failed
                since the creation of this row."
        ::= { slbRealTableEntry 16 }

slbRealRowStatus                        OBJECT-TYPE
        SYNTAX          RowStatus
        MAX-ACCESS      read-create
        STATUS          current
        DESCRIPTION
                "The object used by a management station to create
                or delete the row entry in slbRealTable following the
                RowStatus textual convention."
        ::= { slbRealTableEntry 17 }

slbRealTotalConnections              OBJECT-TYPE
        SYNTAX          Counter32
        MAX-ACCESS      read-only
        STATUS          current
        DESCRIPTION
                "The number of assigned connections handled by this
                real server since this server was configured."
        ::= { slbRealTableEntry 18 }

slbRealHCTotalConnections            OBJECT-TYPE
        SYNTAX          Counter64
        MAX-ACCESS      read-only
        STATUS          current
        DESCRIPTION
                "The number of assigned connections handled by this
                real server since this server was configured.  This
                is the 64-bit version of slbRealTotalConnections."
        ::= { slbRealTableEntry 19 }

--  *************************************************************
--  *                                                           *
--  * SLB - Virtual Server Table                                *
--  *                                                           *
--  *************************************************************

slbVirtualServerTable                   OBJECT-TYPE
        SYNTAX          SEQUENCE OF SlbVirtualServerTableEntry
        MAX-ACCESS      not-accessible
        STATUS          current
        DESCRIPTION
                "Table of virtual servers.  Columnar objects can be
                modified when the row is 'active'.  Rows can be
                created and destroyed.  Entries are added to this
                table via slbVirtualRowStatus in accordance with the
                RowStatus convention."
        ::= { slbVirtualServers 1 }

slbVirtualServerTableEntry              OBJECT-TYPE
        SYNTAX          SlbVirtualServerTableEntry
        MAX-ACCESS      not-accessible
        STATUS          current
        DESCRIPTION
                "Information about a particular virtual server served
                by a particular local SLB entity."
        INDEX   {
                slbEntity,
                slbVirtualServerName
        }
        ::= { slbVirtualServerTable 1 }

SlbVirtualServerTableEntry ::= SEQUENCE {
        slbVirtualServerName                    SlbServerString,
        slbVirtualServerState                   SlbVirtualServState,
        slbVirtualIndex                         Unsigned32,
        slbVirtualIpAddress                     IpAddress,
        slbVirtualPort                          CiscoPort,
        slbVirtualProtocol                      CiscoIpProtocol,
        slbVirtualService                       SlbVirtualService,
        slbVirtualAdvertise                     TruthValue,
        slbVirtualFarmName                      SlbServerString,
        slbVirtualDelayTimer                    Unsigned32,
        slbVirtualIdleTimer                     Unsigned32,
        slbVirtualStickyTimer                   TimeInterval,
        slbVirtualStickyGroup                   Unsigned32,
        slbVirtualSynguardCount                 Unsigned32,
        slbVirtualSynguardPeriod                Unsigned32,
        slbVirtualRowStatus                     RowStatus,
        slbVirtualNumberOfConnections           Gauge32,
        slbVirtualTotalConnections              Counter32,
        slbVirtualHCTotalConnections            Counter64,
        slbVirtualMask                          IpAddress
}

slbVirtualServerName                    OBJECT-TYPE
        SYNTAX          SlbServerString
        MAX-ACCESS      not-accessible
        STATUS          current
        DESCRIPTION
                "The name of the virtual server."
        ::= { slbVirtualServerTableEntry 1 }

slbVirtualServerState                   OBJECT-TYPE
        SYNTAX          SlbVirtualServState
        MAX-ACCESS      read-create
        STATUS          current
        DESCRIPTION
                "The state of virtual server."
        DEFVAL          { outOfService }
        ::= { slbVirtualServerTableEntry  2 }

slbVirtualIndex                         OBJECT-TYPE
        SYNTAX          Unsigned32
        MAX-ACCESS      read-only
        STATUS          current
        DESCRIPTION
                "The index assigned to a virtual server, used to
                correlate connections with virtual servers."
        ::= { slbVirtualServerTableEntry 3 }

slbVirtualIpAddress                     OBJECT-TYPE
        SYNTAX          IpAddress
        MAX-ACCESS      read-create
        STATUS          current
        DESCRIPTION
                "The IP address of this virtual server."
        DEFVAL          { 0 }
        ::= { slbVirtualServerTableEntry 4 }

slbVirtualPort                          OBJECT-TYPE
        SYNTAX          CiscoPort
        MAX-ACCESS      read-create
        STATUS          current
        DESCRIPTION
                "The port of this virtual server."
        DEFVAL          { 0 }
        ::= { slbVirtualServerTableEntry 5 }

slbVirtualProtocol                      OBJECT-TYPE
        SYNTAX          CiscoIpProtocol
        MAX-ACCESS      read-create
        STATUS          current
        DESCRIPTION
                "The protocol for this virtual server."
        DEFVAL          { 0 }
        ::= { slbVirtualServerTableEntry 6 }

slbVirtualService                       OBJECT-TYPE
        SYNTAX          SlbVirtualService
        MAX-ACCESS      read-create
        STATUS          current
        DESCRIPTION
                "The service setting for this virtual server.  Setting
                this to other than 'none' results in an association
                being formed between clients using this service and
                this virtual server. Subsequent packets from clients
                requiring this service will be forwarded to the
                nominated real server."
        DEFVAL          { none }
        ::= { slbVirtualServerTableEntry 7 }

slbVirtualAdvertise                     OBJECT-TYPE
        SYNTAX          TruthValue
        MAX-ACCESS      read-create
        STATUS          current
        DESCRIPTION
                "The setting for virtual address advertising.  It is
                set to 'true' if this virtual server has added a static
                route to the routing table attracting traffic destined
                for slbVirtualIpAddress."
        DEFVAL          { false }
        ::= { slbVirtualServerTableEntry 8 }

slbVirtualFarmName                      OBJECT-TYPE
        SYNTAX          SlbServerString
        MAX-ACCESS      read-create
        STATUS          current
        DESCRIPTION
                "The name of virtual server farm bound to this virtual
                server."
        DEFVAL          { "               " }
        ::= { slbVirtualServerTableEntry 9 }

slbVirtualDelayTimer                    OBJECT-TYPE
        SYNTAX          Unsigned32 ( 1..600 )
        UNITS           "seconds"
        MAX-ACCESS      read-create
        STATUS          current
        DESCRIPTION
                "The amount of time this SLB entity will maintain TCP
                connection context after a connection has terminated."
        DEFVAL          { 10 }
        ::= { slbVirtualServerTableEntry 10 }

slbVirtualIdleTimer                     OBJECT-TYPE
        SYNTAX          Unsigned32 ( 10..65535 )
        UNITS           "seconds"
        MAX-ACCESS      read-create
        STATUS          current
        DESCRIPTION
                "The amount of time this SLB entity will maintain
                connection information in the absence of packet
                activity for a connection. When the service is 
                configured as 'gtp', this is the amount of time 
                the SLB entity will forward SGSN retries for a 
                SLB session to the same GGSN"
        DEFVAL          { 3600 }
        ::= { slbVirtualServerTableEntry 11 }

slbVirtualStickyTimer                   OBJECT-TYPE
        SYNTAX          TimeInterval
        MAX-ACCESS      read-create
        STATUS          current
        DESCRIPTION
                "The amount of time that a connection's real server is
                remembered after a connection has terminated."
        DEFVAL          { 0 }
        ::= { slbVirtualServerTableEntry 12 }

slbVirtualStickyGroup                   OBJECT-TYPE
        SYNTAX          Unsigned32
        MAX-ACCESS      read-create
        STATUS          current
        DESCRIPTION
                "The group ID associated with the 'sticky group' that
                this virtual server is placed in.  A value of zero
                indicates that no 'sticky group' is associated with
                this virtual server."
        DEFVAL          { 0 }
        ::= { slbVirtualServerTableEntry 13 }

slbVirtualSynguardCount                 OBJECT-TYPE
        SYNTAX          Unsigned32
        MAX-ACCESS      read-create
        STATUS          current
        DESCRIPTION
                "The number of unanswered SYNs that are allowed to be
                outstanding to this virtual server. After this number
                is reached, SYNs are dropped depending on the value
                of slbVirtualSynguardPeriod."
        DEFVAL          { 0 }
        ::= { slbVirtualServerTableEntry 14 }

slbVirtualSynguardPeriod                OBJECT-TYPE
        SYNTAX          Unsigned32
        UNITS           "milliseconds"
        MAX-ACCESS      read-create
        STATUS          current
        DESCRIPTION
                "The interval of time that this virtual server can
                have outstanding unanswered SYNs.  This is used
                with slbVirtualSynguardCount to limit outstanding
                SYNs."
        DEFVAL          { 0 }
        ::= { slbVirtualServerTableEntry 15 }

slbVirtualRowStatus                     OBJECT-TYPE
        SYNTAX          RowStatus
        MAX-ACCESS      read-create
        STATUS          current
        DESCRIPTION
                "This object is used by a management station to create
                or delete the row entry in slbVirtualServerTable
                following the RowStatus textual convention."
        ::= { slbVirtualServerTableEntry 16 }

slbVirtualNumberOfConnections           OBJECT-TYPE
        SYNTAX          Gauge32
        MAX-ACCESS      read-only
        STATUS          current
        DESCRIPTION
                "The number of currently assigned connections being
                handled by this virtual server."
        ::= { slbVirtualServerTableEntry  17 }

slbVirtualTotalConnections              OBJECT-TYPE
        SYNTAX          Counter32
        MAX-ACCESS      read-only
        STATUS          current
        DESCRIPTION
                "The number of assigned connections handled by this
                virtual server since this server was configured."
        ::= { slbVirtualServerTableEntry  18 }

slbVirtualHCTotalConnections            OBJECT-TYPE
        SYNTAX          Counter64
        MAX-ACCESS      read-only
        STATUS          current
        DESCRIPTION
                "The number of assigned connections handled by this
                virtual server since this server was configured.  This
                is the 64-bit version of slbVirtualTotalConnections."
        ::= { slbVirtualServerTableEntry  19 }

slbVirtualMask                          OBJECT-TYPE
        SYNTAX          IpAddress
        MAX-ACCESS      read-create
        STATUS          current
        DESCRIPTION
                "The IP subnet mask which is applied to the address 
                 of this virtual server for traffic filtering."
        DEFVAL { 'ffffffff'H } -- 255.255.255.255
        ::= { slbVirtualServerTableEntry 20 }


-- Virtual Server Info table

slbVServerInfoTable OBJECT-TYPE
        SYNTAX          SEQUENCE OF SlbVServerInfoTableEntry
        MAX-ACCESS      not-accessible
        STATUS          current
        DESCRIPTION
                "This table provides information on virtual servers."
        ::= { slbVirtualServers 2 }

slbVServerInfoTableEntry              OBJECT-TYPE
        SYNTAX          SlbVServerInfoTableEntry
        MAX-ACCESS      not-accessible
        STATUS          current
        DESCRIPTION
                "An entry in virtual server table.  An entry
                gets created when class map is associated with
                policy map.  An entry gets deleted when a class-map
                is disassociated with the policy-map."
        INDEX   { slbEntity, slbVServerIndex }
        ::= { slbVServerInfoTable 1 }

SlbVServerInfoTableEntry ::= SEQUENCE {
        slbVServerIndex                    Unsigned32,
        slbVServerClassMap                 SnmpAdminString,
        slbVServerPolicyMap                SnmpAdminString,
        slbVServerState                    SlbVirtualServState,
        slbVServerStateChangeDescr         SnmpAdminString,
        slbVServerNumberOfConnections      Gauge32,
        slbVServerTotalConnections         Counter32
}

slbVServerIndex OBJECT-TYPE
        SYNTAX          Unsigned32 (1..4294967295)
        MAX-ACCESS      not-accessible
        STATUS          current
        DESCRIPTION
                "An unique identifier for the virtual server.
                This value is unique for a combination of
                class map and a policy map."
        ::= { slbVServerInfoTableEntry  1 }

slbVServerClassMap  OBJECT-TYPE
        SYNTAX     SnmpAdminString
        MAX-ACCESS read-only
        STATUS     current
        DESCRIPTION
                "This object contains the class map 
                in which this virtual server is
                associated with it.  A class-map is 
                used to classify a set of traffic 
                with which actions may be associated."
        ::= { slbVServerInfoTableEntry  2 }

slbVServerPolicyMap OBJECT-TYPE
        SYNTAX          SnmpAdminString
        MAX-ACCESS      read-only
        STATUS          current
        DESCRIPTION
            "This object identifies the policy map.
            A policy-map can be used to identify
            various policies such as security policies or
           load balancing policies.  A class map
           can be associated with a policy map."
        ::= { slbVServerInfoTableEntry  3 }

slbVServerState  OBJECT-TYPE
        SYNTAX     SlbVirtualServState
        MAX-ACCESS read-only
        STATUS     current
        DESCRIPTION
                "The state of virtual server."
        ::= { slbVServerInfoTableEntry  4 }

slbVServerStateChangeDescr OBJECT-TYPE         
    SYNTAX     SnmpAdminString
    MAX-ACCESS read-only
    STATUS     current
    DESCRIPTION
        "This object contains the descriptive
        text qualifying the reason for the
        value in slbVServerState.

         Examples:
           OK
           Policy not configured
           Server Farm failed
           Real Server failed."
        ::= { slbVServerInfoTableEntry  5 }

slbVServerNumberOfConnections OBJECT-TYPE
        SYNTAX          Gauge32
        MAX-ACCESS      read-only
        STATUS          current
        DESCRIPTION
                "The number of currently assigned connections being
                handled by this virtual server."
        ::= { slbVServerInfoTableEntry  6 }

slbVServerTotalConnections OBJECT-TYPE
        SYNTAX          Counter32
        MAX-ACCESS      read-only
        STATUS          current
        DESCRIPTION
                "The number of assigned connections handled by this
                virtual server since this server was configured."
        ::= { slbVServerInfoTableEntry  7 }


-- IP Address table for Virtual Server 

slbVServerIPTable OBJECT-TYPE
        SYNTAX          SEQUENCE OF SlbVServerIPTableEntry
        MAX-ACCESS      not-accessible
        STATUS          current
        DESCRIPTION
                "This table contains the IP Addresses 
                configured for virtual servers.  A virtual
                server can have more than one IP Address
                configured in it."
        ::= { slbVirtualServers 3 }

slbVServerIPTableEntry              OBJECT-TYPE
        SYNTAX          SlbVServerIPTableEntry
        MAX-ACCESS      not-accessible
        STATUS          current
        DESCRIPTION
                "An entry in the virtual server IP table.
                Each entry contains virtual server attributes 
                that are used for server loadbalancing decisions."
        INDEX   {
                slbEntity,
                slbVServerIndex,
                slbVServerObjectIndex
        }
        ::= { slbVServerIPTable 1 }

SlbVServerIPTableEntry ::= SEQUENCE {
        slbVServerObjectIndex      Unsigned32,
        slbVServerIpAddressType    InetAddressType,
        slbVServerIpAddress        InetAddress,
        slbVServerIpMask           InetAddressPrefixLength,
        slbVServerProtocol         CiscoIpProtocol,
        slbVServerPortLow          InetPortNumber,
        slbVServerPortHigh         InetPortNumber,
        slbVServerStorageType      StorageType,
        slbVServerRowStatus        RowStatus
}

slbVServerObjectIndex OBJECT-TYPE
        SYNTAX     Unsigned32 (1..4294967295)
        MAX-ACCESS not-accessible
        STATUS     current
        DESCRIPTION
                "The index identifying an entry applicable to
                the same virtual server identified by slbVServerIndex."
        ::= { slbVServerIPTableEntry 1 }

slbVServerIpAddressType OBJECT-TYPE
        SYNTAX     InetAddressType
        MAX-ACCESS read-create
        STATUS     current
        DESCRIPTION
                "The type of IP address configured
                in slbVServerIpAddress."
        DEFVAL {ipv4}
        ::= { slbVServerIPTableEntry 2 }

slbVServerIpAddress OBJECT-TYPE
        SYNTAX      InetAddress
        MAX-ACCESS  read-create
        STATUS      current
        DESCRIPTION
                "The IP address of the virtual server.
                The type of IP address is provided in
                slbVServerIpAddressType."
        ::= { slbVServerIPTableEntry 3 }

slbVServerIpMask     OBJECT-TYPE
        SYNTAX     InetAddressPrefixLength
        MAX-ACCESS read-create
        STATUS     current
        DESCRIPTION
                "This object is subnet mask for the slbVServerIpAddress.
                The IP subnet mask is applied to the address 
                of this virtual server for traffic filtering.
                The value 0 is used to specifiy that the address
                mask of the virtual server is unknown or not used."
        DEFVAL { 0 }
        ::= { slbVServerIPTableEntry 4 }

slbVServerProtocol OBJECT-TYPE
        SYNTAX     CiscoIpProtocol
        MAX-ACCESS read-create
        STATUS     current
        DESCRIPTION
                "The protocol for the virtual server IP address."
        ::= { slbVServerIPTableEntry 5 }

slbVServerPortLow OBJECT-TYPE
        SYNTAX     InetPortNumber
        MAX-ACCESS read-create
        STATUS     current
        DESCRIPTION
                "This object identifies the port number of the
                virtual server that is used in loadbalancing decisions.
                This has to be less than or equal to slbVServerPortHigh."
        DEFVAL {0}
        ::= { slbVServerIPTableEntry 6 }

slbVServerPortHigh OBJECT-TYPE
        SYNTAX     InetPortNumber
        MAX-ACCESS read-create
        STATUS     current
        DESCRIPTION
                "This object identifies the upper bound of 
                the port number of the virtual server that is
                used in loadbalancing decisions. 
                This has to be greater than or equal to slbVServerPortLow."
        DEFVAL {0}
        ::= { slbVServerIPTableEntry 7 }

slbVServerStorageType OBJECT-TYPE
        SYNTAX     StorageType
        MAX-ACCESS read-create
        STATUS     current
        DESCRIPTION 
            "The storage type for this conceptual row."
        DEFVAL      { volatile }
        ::= { slbVServerIPTableEntry 8 }

slbVServerRowStatus OBJECT-TYPE
        SYNTAX          RowStatus
        MAX-ACCESS      read-create
        STATUS          current
        DESCRIPTION
                "This object is used to create/delete entries in
                this table."
        ::= { slbVServerIPTableEntry 9 }
        
--  *************************************************************
--  *                                                           *
--  * SLB - Connection Table                                    *
--  *                                                           *
--  *************************************************************

slbConnectionTable                      OBJECT-TYPE
        SYNTAX          SEQUENCE OF SlbConnectionTableEntry
        MAX-ACCESS      not-accessible
        STATUS          current
        DESCRIPTION
                "Table of connections being load-balanced by SLB."
        ::= { slbConnections 1 }

slbConnectionTableEntry                 OBJECT-TYPE
        SYNTAX          SlbConnectionTableEntry
        MAX-ACCESS      not-accessible
        STATUS          current
        DESCRIPTION
                "A list of attributes for a particular SLB connection."
        INDEX   {
                slbEntity,
                slbConnectionIndex,
                slbConnectionVirtualIpAddress,
                slbConnectionVirtualPort,
                slbConnectionProtocol,
                slbConnectionClientIpAddr,
                slbConnectionClientPort
        }
        ::= { slbConnectionTable 1 }

SlbConnectionTableEntry ::= SEQUENCE {
        slbConnectionIndex              Unsigned32,
        slbConnectionVirtualIpAddress   IpAddress,
        slbConnectionVirtualPort        CiscoPort,
        slbConnectionClientIpAddr       IpAddress,
        slbConnectionClientPort         CiscoPort,
        slbConnectionProtocol           CiscoIpProtocol,
        slbConnectionState              SlbConnectionState,
        slbConnectionRealIpAddr         IpAddress,
        slbConnectionServerPort         CiscoPort,
        slbConnectionNumCacheEntries    Gauge32,
        slbConnectionSynCount           Counter32
}

slbConnectionIndex                      OBJECT-TYPE
        SYNTAX          Unsigned32
        MAX-ACCESS      not-accessible
        STATUS          current
        DESCRIPTION
                "The index to internal structures for the connection."
        ::= { slbConnectionTableEntry 1 }

slbConnectionVirtualIpAddress           OBJECT-TYPE
        SYNTAX          IpAddress
        MAX-ACCESS      not-accessible
        STATUS          current
        DESCRIPTION
                "The IP address of the virtual server."
        ::= { slbConnectionTableEntry 2 }

slbConnectionVirtualPort                OBJECT-TYPE
        SYNTAX          CiscoPort
        MAX-ACCESS      not-accessible
        STATUS          current
        DESCRIPTION
                "The port of the virtual server."
        ::= { slbConnectionTableEntry 3 }

slbConnectionProtocol                   OBJECT-TYPE
        SYNTAX          CiscoIpProtocol
        MAX-ACCESS      not-accessible
        STATUS          current
        DESCRIPTION
                "The connection protocol."
        ::= { slbConnectionTableEntry 4 }

slbConnectionClientIpAddr               OBJECT-TYPE
        SYNTAX          IpAddress
        MAX-ACCESS      not-accessible
        STATUS          current
        DESCRIPTION
                "The client IP address."
        ::= { slbConnectionTableEntry 5 }

slbConnectionClientPort                 OBJECT-TYPE
        SYNTAX          CiscoPort
        MAX-ACCESS      not-accessible
        STATUS          current
        DESCRIPTION
                "The client port."
        ::= { slbConnectionTableEntry 6 }

slbConnectionState                      OBJECT-TYPE
        SYNTAX          SlbConnectionState
        MAX-ACCESS      read-only
        STATUS          current
        DESCRIPTION
                "The current state of this connection."
        ::= { slbConnectionTableEntry 7 }

slbConnectionRealIpAddr                 OBJECT-TYPE
        SYNTAX          IpAddress
        MAX-ACCESS      read-only
        STATUS          current
        DESCRIPTION
                "The IP Address of the real server to which this
                client is being load-balanced."
        ::= { slbConnectionTableEntry 8 }

slbConnectionServerPort                 OBJECT-TYPE
        SYNTAX          CiscoPort
        MAX-ACCESS      read-only
        STATUS          current
        DESCRIPTION
                "The port number at the real server to which this
                client is being load-balanced."
        ::= { slbConnectionTableEntry 9 }

slbConnectionNumCacheEntries            OBJECT-TYPE
        SYNTAX          Gauge32
        MAX-ACCESS      read-only
        STATUS          current
        DESCRIPTION
                "The number of netflow cache entries for this
                connection.  An entry for a terminated connection
                cannot be deleted while this number is non-zero."
        ::= { slbConnectionTableEntry 10 }

slbConnectionSynCount                   OBJECT-TYPE
        SYNTAX          Counter32
        MAX-ACCESS      read-only
        STATUS          current
        DESCRIPTION
                "The number of SYNs seen from client."
        ::= { slbConnectionTableEntry 11 }

--  *************************************************************
--  *                                                           *
--  * SLB - Virtual Client Table                                *
--  *                                                           *
--  *************************************************************

slbVirtualClientTable                   OBJECT-TYPE
        SYNTAX          SEQUENCE OF SlbVirtualClientTableEntry
        MAX-ACCESS      not-accessible
        STATUS          current
        DESCRIPTION
                "Table of virtual clients for a particular virtual
                server.  Columnar objects can be modified when the
                row is 'active'.  Entries are added to this table via
                slbVirtualClientRowStatus in accordance with the
                RowStatus convention."
        ::= { slbVirtualClients 1 }

slbVirtualClientTableEntry              OBJECT-TYPE
        SYNTAX          SlbVirtualClientTableEntry
        MAX-ACCESS      not-accessible
        STATUS          current
        DESCRIPTION
                "Information about a particular client range for a
                virtual server served by a particular local SLB entity.
                If client ranges overlap, the entry with the longest
                match will be used."
        INDEX   {
                slbEntity,
                slbVirtualServerName,
                slbVirtualClientIpAddress,
                slbVirtualClientMask
        }
        ::= { slbVirtualClientTable 1 }

SlbVirtualClientTableEntry ::= SEQUENCE {
        slbVirtualClientIpAddress       IpAddress,
        slbVirtualClientMask            IpAddress,
        slbVirtualClientExclude         TruthValue,
        slbVirtualClientRowStatus       RowStatus
}

slbVirtualClientIpAddress               OBJECT-TYPE
        SYNTAX        IpAddress
        MAX-ACCESS    not-accessible
        STATUS        current
        DESCRIPTION
                "The IP address of the client.  It is used along with
                the slbVirtualClientMask to represent subsets of client
                traffic being handled by the particular virtual server."
        ::= { slbVirtualClientTableEntry 1 }

slbVirtualClientMask                    OBJECT-TYPE
        SYNTAX        IpAddress
        MAX-ACCESS    not-accessible
        STATUS        current
        DESCRIPTION
                "The general purpose mask of the client.  It is used
                along with the slbVirtualClientIpAddress to represent
                subsets of client traffic being handled by the
                particular virtual server."
        ::= { slbVirtualClientTableEntry 2 }

slbVirtualClientExclude                 OBJECT-TYPE
        SYNTAX        TruthValue
        MAX-ACCESS    read-create
        STATUS        current
        DESCRIPTION
                "The truth value that determines if the client range
                should be included or excluded on the virtual server."
        DEFVAL        { false }
        ::= { slbVirtualClientTableEntry 3 }

slbVirtualClientRowStatus               OBJECT-TYPE
        SYNTAX          RowStatus
        MAX-ACCESS      read-create
        STATUS          current
        DESCRIPTION
                "The row status is used by a management station to
                create or delete the row entry in slbVirtualClientTable
                following the RowStatus textual convention."
        ::= { slbVirtualClientTableEntry 4 }
        
--  *************************************************************
--  *                                                           *
--  * SLB - Sticky Table                                        *
--  *                                                           *
--  *************************************************************

slbStickyObjectTable                    OBJECT-TYPE
        SYNTAX          SEQUENCE OF SlbStickyObjectTableEntry
        MAX-ACCESS      not-accessible
        STATUS          current
        DESCRIPTION
                "Table of sticky objects.  Sticky objects allow
                related connections to be sent to the same real
                server on a per client basis.  Sticky objects are
                useful for FTP and SSL connections.  Columnar objects
                can be modified when the row is 'active'.  Entries
                are added to this table via slbStickyObjectRowStatus
                in accordance with the RowStatus convention."
        ::= { slbStickyObjects 1 }

slbStickyObjectTableEntry               OBJECT-TYPE
        SYNTAX          SlbStickyObjectTableEntry
        MAX-ACCESS      not-accessible
        STATUS          current
        DESCRIPTION
                "Information about a particular sticky object for 
                clients at a particular IP address served by a
                particular local SLB entity."
        INDEX   {
                slbEntity,
                slbStickyObjectGroupId,
                slbStickyObjectClientIpAddress
        }
        ::= { slbStickyObjectTable 1 }

SlbStickyObjectTableEntry ::= SEQUENCE {
        slbStickyObjectClientIpAddress  IpAddress,
        slbStickyObjectGroupId          Unsigned32,
        slbStickyObjectRealIpAddress    IpAddress,
        slbStickyObjectConnectionCount  Gauge32,
        slbStickyObjectFtpControlCount  Gauge32,
        slbStickyObjectRowStatus        RowStatus
}

slbStickyObjectGroupId                  OBJECT-TYPE
        SYNTAX          Unsigned32 ( 1..65535 )
        MAX-ACCESS      not-accessible
        STATUS          current
        DESCRIPTION
                "The group ID for this sticky object."
        ::= { slbStickyObjectTableEntry 1 }

slbStickyObjectClientIpAddress          OBJECT-TYPE
        SYNTAX          IpAddress
        MAX-ACCESS      not-accessible
        STATUS          current
        DESCRIPTION
                "The client IP address with which this object is
                associated."
        ::= { slbStickyObjectTableEntry 2 }

slbStickyObjectRealIpAddress            OBJECT-TYPE
        SYNTAX          IpAddress
        MAX-ACCESS      read-create
        STATUS          current
        DESCRIPTION
                "The real server IP address selected for all clients
                bound to this sticky object."
        DEFVAL          { 0 }
        ::= { slbStickyObjectTableEntry 3 }

slbStickyObjectConnectionCount          OBJECT-TYPE
        SYNTAX          Gauge32
        MAX-ACCESS      read-only
        STATUS          current
        DESCRIPTION
                "The number of connections currently associated with
                this sticky object."
        ::= { slbStickyObjectTableEntry 4 }

slbStickyObjectFtpControlCount          OBJECT-TYPE
        SYNTAX          Gauge32
        MAX-ACCESS      read-only
        STATUS          current
        DESCRIPTION
                "The number of FTP control connections currently
                associated with this sticky object."
        ::= { slbStickyObjectTableEntry 5 }

slbStickyObjectRowStatus                OBJECT-TYPE
        SYNTAX          RowStatus
        MAX-ACCESS      read-create
        STATUS          current
        DESCRIPTION
                "The row status is used by a management station to
                create or delete the row entry in slbStickyObjectTable
                following the RowStatus textual convention."
        ::= { slbStickyObjectTableEntry 6 }

--  *************************************************************
--  *                                                           *
--  * Notification Truth Values                                 *
--  *                                                           *
--  *************************************************************

cSlbVirtStateChangeNotifEnabled OBJECT-TYPE
        SYNTAX      TruthValue
        MAX-ACCESS  read-write
        STATUS      current
        DESCRIPTION 
                "The virtual server notification truth value.
                'true'  Indicates that ciscoSlbVirtualStateChange
                        notification is to be generated when the state
                        changes. That is, the notification generation 
                        is enabled.
                'false' Indicates that ciscoSlbVirtualStateChange
                        notification generation is disabled."
        DEFVAL { false }
        ::= { slbNotificationObjects 1 }
 
cSlbRealStateChangeNotifEnabled OBJECT-TYPE
        SYNTAX      TruthValue
        MAX-ACCESS  read-write
        STATUS      current
        DESCRIPTION 
                "The real server notification truth value.
                'true'  Indicates that ciscoSlbRealStateChange
                        notification is to be generated when the state
                        changes. That is, the notification generation 
                        is enabled.
                'false' Indicates that ciscoSlbRealStateChange
                        notification generation is disabled."
        DEFVAL { false }
        ::= { slbNotificationObjects 2 }

cSlbVServerStateChangeNotifEnabled OBJECT-TYPE
        SYNTAX      TruthValue
        MAX-ACCESS  read-write
        STATUS      current
        DESCRIPTION 
                "The virtual server notification truth value.
                This object controls the generation of following
                notifications:
                    ciscoSlbVServerStateChange
                    ciscoSlbVServerVIPStateChange
 
                'true'  Indicates whether notification is to be
                        generated when the state changes. That is, 
                        the notification generation is enabled.
                'false' Indicates notification should not be generated.
                        That is, the notification generation is disabled."
        DEFVAL { false }
        ::= { slbNotificationObjects 3 }

--  *************************************************************
--  *                                                           *
--  * SLB - Dynamic Feedback Protocol (DFP) Password            *
--  *                                                           *
--  *************************************************************

slbDfpPasswordTable                     OBJECT-TYPE
        SYNTAX          SEQUENCE OF SlbDfpPasswordTableEntry
        MAX-ACCESS      not-accessible
        STATUS          current
        DESCRIPTION
                "A table of password values which a local Server Load
                Balancing Manager uses so that it can communicate with
                remote DFP agents.  Entries are added to this table via
                slbDfpPasswordRowStatus in accordance with the
                RowStatus convention.  Columnar objects can be modified
                when in row is 'active'. Rows can be created and
                destroyed."
        ::= { slbDfpPassword 1 }

slbDfpPasswordTableEntry                OBJECT-TYPE
        SYNTAX          SlbDfpPasswordTableEntry
        MAX-ACCESS      not-accessible
        STATUS          current
        DESCRIPTION
                "An entry in this table represents the password used
                by a particular DFP manager (identified by slbEntity)
                when it exchanges messages with DFP agents."
        INDEX   {
                slbEntity
        }
        ::= { slbDfpPasswordTable 1 }

SlbDfpPasswordTableEntry ::= SEQUENCE {
        slbDfpPasswordPending   SlbPasswordString,
        slbDfpPasswordTimeout   TimeInterval,
        slbDfpPasswordRowStatus RowStatus
}

slbDfpPasswordPending                   OBJECT-TYPE
        SYNTAX          SlbPasswordString
        MAX-ACCESS      read-create
        STATUS          current
        DESCRIPTION
                "The pending password which will be used by DFP for MD5
                authentication within password timeout ticks.  When
                read, this object returns a zero-length string and
                writing a zero-length string unsets the password.  If
                this object is modified twice within the time interval
                given by slbDfpPasswordTimeout, the password and
                timeout of the first modification are forgotten and
                replaced by the password and timeout of the second."
        DEFVAL          { "" }
        ::= { slbDfpPasswordTableEntry 1 }

slbDfpPasswordTimeout                   OBJECT-TYPE
        SYNTAX          TimeInterval
        MAX-ACCESS      read-create
        STATUS          current
        DESCRIPTION
                "The time interval between the setting of the pending
                password and the removal of the current password."
        DEFVAL          { 0 }
        ::= { slbDfpPasswordTableEntry 2 }

slbDfpPasswordRowStatus                 OBJECT-TYPE
        SYNTAX          RowStatus
        MAX-ACCESS      read-create
        STATUS          current
        DESCRIPTION
                "The object is used by a management station to create
                or delete the row entry in slbDfpPasswordTable
                following the RowStatus textual convention."
        ::= { slbDfpPasswordTableEntry 3 }

--  *************************************************************
--  *                                                           *
--  * SLB - Dynamic Feedback Protocol Agent Table               *
--  *                                                           *
--  *************************************************************

slbDfpAgentTable                        OBJECT-TYPE
        SYNTAX          SEQUENCE OF SlbDfpAgentTableEntry
        MAX-ACCESS      not-accessible
        STATUS          current
        DESCRIPTION
                "A table of remote DFP agents with which the local
                DFP managers communicate.  Rows can be created and
                destroyed. Columnar objects can be modified when the
                row is 'active'.  Entries are added to this table via
                slbDfpAgentRowStatus in accordance with the RowStatus
                convention."
        ::= { slbDfpAgents 1 }

slbDfpAgentTableEntry                   OBJECT-TYPE
        SYNTAX          SlbDfpAgentTableEntry
        MAX-ACCESS      not-accessible
        STATUS          current
        DESCRIPTION
                "Information about the communication between a local
                DFP manager and a particular remote DFP agent."
        INDEX   {
                slbEntity,
                slbDfpAgentIpAddress,
                slbDfpAgentPort
        }
        ::= { slbDfpAgentTable 1 }

SlbDfpAgentTableEntry ::= SEQUENCE {
        slbDfpAgentIpAddress    IpAddress,
        slbDfpAgentPort         CiscoPort,
        slbDfpAgentState        SlbDfpAgentState,
        slbDfpAgentTimeout      TimeInterval,
        slbDfpAgentRetryCount   Unsigned32,
        slbDfpAgentInterval     TimeInterval,
        slbDfpAgentRowStatus    RowStatus
}

slbDfpAgentIpAddress                    OBJECT-TYPE
        SYNTAX          IpAddress
        MAX-ACCESS      not-accessible
        STATUS          current
        DESCRIPTION
                "The DFP agent's IP address."
        ::= { slbDfpAgentTableEntry 1 }

slbDfpAgentPort                         OBJECT-TYPE
        SYNTAX          CiscoPort
        MAX-ACCESS      not-accessible
        STATUS          current
        DESCRIPTION
                "The DFP agent's port."
        ::= { slbDfpAgentTableEntry 2 }

slbDfpAgentState                        OBJECT-TYPE
        SYNTAX          SlbDfpAgentState
        MAX-ACCESS      read-only
        STATUS          current
        DESCRIPTION
                "The state of the DFP agent."
        ::= { slbDfpAgentTableEntry 3 }

slbDfpAgentTimeout                      OBJECT-TYPE
        SYNTAX          TimeInterval
        MAX-ACCESS      read-create
        STATUS          current
        DESCRIPTION
                "Time interval during which the agent must send at
                least one message to the manager."
        ::= { slbDfpAgentTableEntry 4 }

slbDfpAgentRetryCount                   OBJECT-TYPE
        SYNTAX          Unsigned32 ( 0..65535 )
        MAX-ACCESS      read-create
        STATUS          current
        DESCRIPTION
                "The number of times the manager will attempt to
                re-establish a connection with the agent.  If this
                value is exceeded, the agent is placed in 'failed'
                state, and the manager does not attempt to re-establish
                a connection with the agent."
        ::= { slbDfpAgentTableEntry 5 }

slbDfpAgentInterval                     OBJECT-TYPE
        SYNTAX          TimeInterval
        MAX-ACCESS      read-create
        STATUS          current
        DESCRIPTION
                "Time interval before SLB retries connecting to a DFP
                agent."
        ::= { slbDfpAgentTableEntry 6 }

slbDfpAgentRowStatus                    OBJECT-TYPE
        SYNTAX          RowStatus
        MAX-ACCESS      read-create
        STATUS          current
        DESCRIPTION
                "The row status is used by a management station to
                create or delete the row entry in slbDfpAgentTable
                following the RowStatus textual convention."
        ::= { slbDfpAgentTableEntry 7 }

--  *************************************************************
--  *                                                           *
--  * SLB - Dynamic Feedback Protocol Real Server Table         *
--  *                                                           *
--  *************************************************************

slbDfpRealTable                         OBJECT-TYPE
        SYNTAX          SEQUENCE OF SlbDfpRealTableEntry
        MAX-ACCESS      not-accessible
        STATUS          current
        DESCRIPTION
                "A table containing information about Real Servers
                obtained through communications between local DFP
                manager and remote DFP agents.  Rows can be created
                and destroyed.  Columnar objects can be modified when
                the row is 'active'.  Entries are added to this table
                via slbDfpRowStatus in accordance with the RowStatus
                convention."
        ::= { slbDfpReal 1 }

slbDfpRealTableEntry                    OBJECT-TYPE
        SYNTAX          SlbDfpRealTableEntry
        MAX-ACCESS      not-accessible
        STATUS          current
        DESCRIPTION
                "Information about a particular real server, within
                one or more server farms (identified with 'bindId'),
                reported by a DFP agent for a particular local SLB
                entity. The real servers are identified by finding
                rows in slbServerFarmTable for which
                slbServerFarmBindId matches slbDfpRealBindId. For each
                identified server farm, extract the slbServerFarmName
                and use this value together with slbDfpRealIpAddress
                and slbDfpRealPort to identify the row in
                slbRealTable."
        INDEX   {
                slbEntity,
                slbDfpRealIpAddress,
                slbDfpRealProtocol,
                slbDfpRealPort,
                slbDfpRealBindId
        }
        ::= { slbDfpRealTable 1 }

SlbDfpRealTableEntry ::= SEQUENCE {
        slbDfpRealIpAddress     IpAddress,
        slbDfpRealProtocol      CiscoIpProtocol,
        slbDfpRealPort          CiscoPort,
        slbDfpRealBindId        Unsigned32,
        slbDfpRealWeight        Unsigned32,
        slbDfpRealRowStatus     RowStatus
}

slbDfpRealIpAddress                     OBJECT-TYPE
        SYNTAX          IpAddress
        MAX-ACCESS      not-accessible
        STATUS          current
        DESCRIPTION
                "The DFP agent's IP address"
        ::= { slbDfpRealTableEntry 1 }

slbDfpRealProtocol                      OBJECT-TYPE
        SYNTAX          CiscoIpProtocol
        MAX-ACCESS      not-accessible
        STATUS          current
        DESCRIPTION
                "The protocol of the real server."
        ::= { slbDfpRealTableEntry 2 }

slbDfpRealPort                          OBJECT-TYPE
        SYNTAX          CiscoPort
        MAX-ACCESS      not-accessible
        STATUS          current
        DESCRIPTION
                "The port number of the real server."
        ::= { slbDfpRealTableEntry 3 }

slbDfpRealBindId                        OBJECT-TYPE
        SYNTAX          Unsigned32
        MAX-ACCESS      not-accessible
        STATUS          current
        DESCRIPTION
                "The Bind ID identifies one or more server farms to
                which the real server belongs. The real servers are
                identified by finding rows in slbServerFarmTable for
                which slbServerFarmBindId matches
                slbDfpRealBindId. For each identified server farm,
                extract the slbServerFarmName and use this value
                together with slbDfpRealIpAddress and slbDfpRealPort
                to identify the row in slbRealTable."
        ::= { slbDfpRealTableEntry 4 }

slbDfpRealWeight                        OBJECT-TYPE
        SYNTAX          Unsigned32 ( 0..65535 )
        MAX-ACCESS      read-create
        STATUS          current
        DESCRIPTION
                "The weight of the real server reported from a
                DFP agent.  The weight represents a relative capacity
                to accept new connections."
        DEFVAL          { 0 }
        ::= { slbDfpRealTableEntry 5 }

slbDfpRealRowStatus                     OBJECT-TYPE
        SYNTAX          RowStatus
        MAX-ACCESS      read-create
        STATUS          current
        DESCRIPTION
                "The row status is used by a management station to
                create or delete the row entry in slbDfpRealTable
                following the RowStatus textual convention."
        ::= { slbDfpRealTableEntry 6 }


--  *************************************************************
--  *                                                           *
--  * SLB - Server Application State Protocol Table             *
--  *                                                           *
--  *************************************************************

slbSaspTable                            OBJECT-TYPE
        SYNTAX          SEQUENCE OF SlbSaspTableEntry
        MAX-ACCESS      not-accessible
        STATUS          current
        DESCRIPTION
                "An entry containing information about the Server
                Application State Protocol (SASP).  There is only one
                entry for each load balancer.  This entry is created
                by the load balancer during initialization."
        ::= { slbSasp 1 }

slbSaspTableEntry                       OBJECT-TYPE
        SYNTAX          SlbSaspTableEntry
        MAX-ACCESS      not-accessible
        STATUS          current
        DESCRIPTION
                "Information for a particular local SLB entity using
                the SASP functionality.  The SASP entry is identified
                by the slbEntity.  The SASP entry includes all of the
                relevant information needed to run SASP on this
                particular slbEntity."
        INDEX   {
                slbEntity
        }
        ::= { slbSaspTable 1 }

SlbSaspTableEntry ::= SEQUENCE {
        slbSaspIdentifier             SnmpAdminString,
        slbSaspEnabled                TruthValue,
        slbSaspHealth                 SlbSaspLBHealth,
        slbSaspRedundancy             SlbSaspRedundancy,
        slbSaspMaxAgents              Unsigned32,
        slbSaspMaxLbWeight            Unsigned32
}

slbSaspIdentifier                       OBJECT-TYPE
        SYNTAX          SnmpAdminString
        MAX-ACCESS      read-write
        STATUS          current
        DESCRIPTION
                "The unique identifier required by SASP for all load
                balancers.  In a redundant system, where there is a
                master and backup load balancer, each load balancer
                must have different identifiers.

                The slbSaspIdentifier may only be changed when the
                slbSaspEnabled object is false.  The default value
                of the slbSaspIdentfier is 'Cisco-<LB>', where <LB>
                is the Cisco acronoym for the load balancer."
        ::= { slbSaspTableEntry 1 }

slbSaspEnabled                          OBJECT-TYPE
        SYNTAX          TruthValue
        MAX-ACCESS      read-write
        STATUS          current
        DESCRIPTION
                "Indicates whether the SASP functionality is
                currently in use by the load balancer.
                'true'  The SASP functionality is enabled on the
                        load balancer.
                'false' The SASP functionality is disabled on the
                        load balancer."
        ::= { slbSaspTableEntry 2 }

slbSaspHealth                           OBJECT-TYPE
        SYNTAX          SlbSaspLBHealth
        MAX-ACCESS      read-only
        STATUS          current
        DESCRIPTION
                "The health value reported to the SASP Agents via the
                Set Load Balancer State Message.  The value represents
                the load balancer's ability to handle SASP messages."
        ::= { slbSaspTableEntry 3 }

slbSaspRedundancy                       OBJECT-TYPE
        SYNTAX          SlbSaspRedundancy
        MAX-ACCESS      read-only
        STATUS          current
        DESCRIPTION
                "The Load Balancer's state in a redundant setup.  The
                Load Balancer may still contact the SASP Agents, which
                are defined in the slbSaspAgentTable, regardless of the
                state.  This is possible because every Load Balancer 
                contacting a SASP Agent is required to have it's own
                unique identifier.  Therefore, the master and backup
                Load Balancer MUST have different unique identifiers."
        ::= { slbSaspTableEntry 4 }

slbSaspMaxAgents                        OBJECT-TYPE
        SYNTAX          Unsigned32
        MAX-ACCESS      read-only
        STATUS          current
        DESCRIPTION
                "The maximum number of SASP Agents that can be
                configured on the Load Balancer.  The SASP Agents are
                configured via the slbSaspAgentTable."
        ::= { slbSaspTableEntry 5 }

slbSaspMaxLbWeight                      OBJECT-TYPE
        SYNTAX          Unsigned32
        MAX-ACCESS      read-only
        STATUS          current
        DESCRIPTION
                "The maximum weight supported by the Load Balancer.
                Any weight reported for a SASP Member, which can be
                found within the slbSaspMemberSaspWeight object, MUST
                be converted to the Load Balancer's weight range.  The
                minimum weight for a Load Balancer MUST be zero.  A
                weight of zero indicates that the SASP Member is down
                and that the Member is not going to receive new 
                connections."
        ::= { slbSaspTableEntry 6 }

--  *************************************************************
--  *                                                           *
--  * SLB - Server Application State Protocol Agent Table       *
--  *                                                           *
--  *************************************************************

slbSaspAgentTable                       OBJECT-TYPE
        SYNTAX          SEQUENCE OF SlbSaspAgentTableEntry
        MAX-ACCESS      not-accessible
        STATUS          current
        DESCRIPTION
                "A table containing information about the SASP Agents.
                Rows can be created and destroyed.  Columnar objects
                can be modified when the row is 'active'.  Entries are
                added to this table via slbSaspAgentRowStatus.

                A SASP Agent is an application or device that is
                responsible for aggregating information regarding the
                performance of a SASP Member.  The information is used
                to calculate a weight that is reported to the load
                balancer."
        ::= { slbSaspAgents 1 }

slbSaspAgentTableEntry                  OBJECT-TYPE
        SYNTAX          SlbSaspAgentTableEntry
        MAX-ACCESS      not-accessible
        STATUS          current
        DESCRIPTION
                "The SASP Agent entry provides information for a
                particular SASP Agent on a local SLB entity.  The
                objects provide the contact information and the current
                connection state of the Agent."
        INDEX   {
                slbEntity,
                slbSaspAgentIpAddressType,
                slbSaspAgentIpAddress,
                slbSaspAgentPort
        }
        ::= { slbSaspAgentTable 1 }

SlbSaspAgentTableEntry ::= SEQUENCE {
        slbSaspAgentIpAddressType     InetAddressType,
        slbSaspAgentIpAddress         InetAddress,
        slbSaspAgentPort              InetPortNumber,
        slbSaspAgentLabel             SnmpAdminString,
        slbSaspAgentState             SlbSaspAgentState,
        slbSaspAgentLastStateChange   DateAndTime,
        slbSaspAgentRowStatus         RowStatus
}

slbSaspAgentIpAddressType               OBJECT-TYPE
        SYNTAX          InetAddressType
        MAX-ACCESS      not-accessible
        STATUS          current
        DESCRIPTION
                "Defines the IP address type used by the
                slbSaspAgentIpAddress."
        ::= { slbSaspAgentTableEntry 1 }

slbSaspAgentIpAddress                   OBJECT-TYPE
        SYNTAX          InetAddress
        MAX-ACCESS      not-accessible
        STATUS          current
        DESCRIPTION
                "The IP address of the SASP Agent that is used for
                weight reporting."
        ::= { slbSaspAgentTableEntry 2 }

slbSaspAgentPort                        OBJECT-TYPE
        SYNTAX          InetPortNumber
        MAX-ACCESS      not-accessible
        STATUS          current
        DESCRIPTION
                "The TCP Port number used when connecting to a SASP
                Agent."
        ::= { slbSaspAgentTableEntry 3 }

slbSaspAgentLabel                       OBJECT-TYPE
        SYNTAX          SnmpAdminString
        MAX-ACCESS      read-create
        STATUS          current
        DESCRIPTION
                "A label that can be assigned by the user for the SASP
                Agent during entry creation.  The label should be in
                a human readable form that describes the SASP Agent.
                The description could be the physical location of the
                Agent or some other field relevant to the user.  The
                label is provided for informational purposes only, and
                it does not affect the operation of the SASP Agent."
        ::= { slbSaspAgentTableEntry 4 }

slbSaspAgentState                       OBJECT-TYPE
        SYNTAX          SlbSaspAgentState
        MAX-ACCESS      read-only
        STATUS          current
        DESCRIPTION
                "The current connection state of the SASP Agent.  The
                load balancer does not give up trying to reach the 
                SASP Agent when it is down."
        ::= { slbSaspAgentTableEntry 5 }

slbSaspAgentLastStateChange             OBJECT-TYPE
        SYNTAX          DateAndTime
        MAX-ACCESS      read-only
        STATUS          current
        DESCRIPTION
                "Displays the date and time of the last state change
                that was incurred by the Agent.  The time that is
                reported is only local time, so the timezone portion
                of the DateAndTime TC will not be specified."
        ::= { slbSaspAgentTableEntry 6 }

slbSaspAgentRowStatus                   OBJECT-TYPE
        SYNTAX          RowStatus
        MAX-ACCESS      read-create
        STATUS          current
        DESCRIPTION
                "The row status is used by a management station to
                create or delete the row entry in slbSaspAgentTable
                following the RowStatus textual convention."
        ::= { slbSaspAgentTableEntry 7 }


--  *************************************************************
--  *                                                           *
--  * SLB - Server Application State Protocol Group Table       *
--  *                                                           *
--  *************************************************************

slbSaspGroupTable                       OBJECT-TYPE
        SYNTAX          SEQUENCE OF SlbSaspGroupTableEntry
        MAX-ACCESS      not-accessible
        STATUS          current
        DESCRIPTION
                "A table containing information about the SASP Groups.
                Rows can be created and destroyed.  Entries are added
                to this table via slbSaspGroupRowStatus.

                A SASP Group is a logical entity used within the SASP
                implementation to group SASP Members that are 
                equivalent in function."
        ::= { slbSaspGroups 1 }

slbSaspGroupTableEntry                  OBJECT-TYPE
        SYNTAX          SlbSaspGroupTableEntry
        MAX-ACCESS      not-accessible
        STATUS          current
        DESCRIPTION
                "The SASP Group table provides the information for a
                particular group associated with a SASP Agent on a
                local SLB entity."
        INDEX   {
                slbEntity,
                slbSaspGroupName
        }
        ::= { slbSaspGroupTable 1 }

SlbSaspGroupTableEntry ::= SEQUENCE {
        slbSaspGroupName              SnmpAdminString,
        slbSaspGroupRowStatus         RowStatus
}

slbSaspGroupName                        OBJECT-TYPE
        SYNTAX          SnmpAdminString
        MAX-ACCESS      not-accessible
        STATUS          current
        DESCRIPTION
               "The SASP group represents the group of SASP Members
               that have the same functional capabilities."
        ::= { slbSaspGroupTableEntry 1 }

slbSaspGroupRowStatus                   OBJECT-TYPE
        SYNTAX          RowStatus
        MAX-ACCESS      read-create
        STATUS          current
        DESCRIPTION
                "The row status is used by a management station to
                create or delete the row entry in slbSaspGroupTable
                following the RowStatus textual convention.  Removing
                the group from this table would have the effect of
                removing all of the SASP Members associated with this
                group from the SASP Member table."
        ::= { slbSaspGroupTableEntry 2 }


--  *************************************************************
--  *                                                           *
--  * SLB - Server Application State Protocol Member Table      *
--  *                                                           *
--  *************************************************************

slbSaspMemberTable                      OBJECT-TYPE
        SYNTAX          SEQUENCE OF SlbSaspMemberTableEntry
        MAX-ACCESS      not-accessible
        STATUS          current
        DESCRIPTION
                "A table containing information about the SASP Members.
                Rows can be created and destroyed.  Columnar objects
                can be modified when the row is 'active'.  Entries are
                added to this table via slbSaspMemberRowStatus.

                A SASP Member is an entity configured on the load
                balancer to help distribute the load for one or more
                services."
        ::= { slbSaspMembers 1 }

slbSaspMemberTableEntry                 OBJECT-TYPE
        SYNTAX          SlbSaspMemberTableEntry
        MAX-ACCESS      not-accessible
        STATUS          current
        DESCRIPTION
                "The SASP Member table provides information about a
                particular SASP Member associated with a SASP Agent.
                Each entry contains all of the weight information
                that is necessary to use SASP on the load balancer.

                It is important that the SASP Member only report to 
                one SASP Agent.  This will avoid any weight reporting
                issues that may arise when the SASP Agent communicates
                with the load balancer."
        INDEX   {
                slbEntity,
                slbSaspAgentIpAddressType,
                slbSaspAgentIpAddress,
                slbSaspAgentPort,
                slbSaspGroupName,
                slbSaspMemberIpAddressType,
                slbSaspMemberIpAddress,
                slbSaspMemberPort,
                slbSaspMemberProtocol
        }
        ::= { slbSaspMemberTable 1 }

SlbSaspMemberTableEntry ::= SEQUENCE {
        slbSaspMemberIpAddressType     InetAddressType,
        slbSaspMemberIpAddress         InetAddress,
        slbSaspMemberPort              InetPortNumber,
        slbSaspMemberProtocol          CiscoIpProtocol,
        slbSaspMemberSaspWeight        Unsigned32,
        slbSaspMemberConfidentWeight   TruthValue,
        slbSaspMemberConvertedWeight   Unsigned32,
        slbSaspMemberDefaultWeight     Unsigned32,
        slbSaspMemberWeightChanges     Counter32,
        slbSaspMemberLastWeightChange  DateAndTime,
        slbSaspMemberRowStatus         RowStatus
}

slbSaspMemberIpAddressType              OBJECT-TYPE
        SYNTAX          InetAddressType
        MAX-ACCESS      not-accessible
        STATUS          current
        DESCRIPTION
                "Defines the IP address type of the
                slbSaspMemberIpAddress."
        ::= { slbSaspMemberTableEntry 1 }

slbSaspMemberIpAddress                  OBJECT-TYPE
        SYNTAX          InetAddress
        MAX-ACCESS      not-accessible
        STATUS          current
        DESCRIPTION
                "The IP address of the member.  The IP address, along
                with the port and protocol type, is registered with the
                SASP Agent.  The SASP Agent includes this information
                when reporting the weights for each member in either the
                'Get Weights Reply' or the 'Send Weights Message'."
        ::= { slbSaspMemberTableEntry 2 }

slbSaspMemberPort                       OBJECT-TYPE
        SYNTAX          InetPortNumber
        MAX-ACCESS      not-accessible
        STATUS          current
        DESCRIPTION
                "The TCP or UDP port number associated with the
                slbSaspMemberIpAddress.  The port number, along with
                the IP address and protocol type, is registered with
                the SASP Agent.  The SASP Agent includes this
                information when reporting the weights for each member
                in either the 'Get Weights Reply' or the 'Send Weights
                Message'."
        ::= { slbSaspMemberTableEntry 3 }

slbSaspMemberProtocol                   OBJECT-TYPE
        SYNTAX          CiscoIpProtocol
        MAX-ACCESS      not-accessible
        STATUS          current
        DESCRIPTION
                "The IP protocol type that is associated with the
                slbSaspMemberIpAddress and slbSaspMemberPort.  The
                protocol type, along with the IP address and port
                number, is registered with the SASP Agent.  The SASP
                Agent includes this information when reporting the
                weights for each member in either the 'Get Weights
                Reply' or the 'Send Weights Message'."
        ::= { slbSaspMemberTableEntry 4 }

slbSaspMemberSaspWeight                 OBJECT-TYPE
        SYNTAX          Unsigned32 ( 0..65535 )
        MAX-ACCESS      read-only
        STATUS          current
        DESCRIPTION
                "The reported weight by the SASP Agent.  The weights
                are reported via the 'Send Weights Message' or in the
                'Get Weights Reply'.  The reported weight MUST be
                converted to be within the Load Balancer's supported
                weight range, specified by the slbSaspMaxLbWeight
                object.  The resulting weight value will be stored in
                the slbSaspMemberConvertedWeight object."
        ::= { slbSaspMemberTableEntry 5 }

slbSaspMemberConfidentWeight            OBJECT-TYPE
        SYNTAX          TruthValue
        MAX-ACCESS      read-only
        STATUS          current
        DESCRIPTION
                "Represents the SASP Agent's confidence in the reported
                weight.
                'true'  Indicates the slbSaspMemberSaspWeight value is
                        accurate and reflects the up-to-date real-time
                        statistics collected by the SASP Agent.
                'false' Indicates the SASP Agent is guessing the weight
                        of the member based on prior knowledge.  It is
                        at the load balancer's discretion whether or not
                        to use this weight.  If not, the default weight
                        must be used (slbSaspMemberDefaultWeight)."
        ::= { slbSaspMemberTableEntry 6 }

slbSaspMemberConvertedWeight            OBJECT-TYPE
        SYNTAX          Unsigned32 ( 0..65535 )
        MAX-ACCESS      read-only
        STATUS          current
        DESCRIPTION
                "The SASP weight converted to the local load balancer
                weight range.  The load balancer's weight range is
                implementation dependent, as is the formula used to
                convert the weight.

                The following formula is an example weight conversion
                that could be used by the load balancer:

                answer => slbSaspMemberConvertedWeight
                maxLbWgt => slbSaspMaxLbWeight
                mbrSaspWgt => slbSaspMemberSaspWeight

                answer = ((mbrSaspWgt * maxLbWgt) / 65535) + 1

                Note: There are two edge cases that need to be
                considered; when the mbrSaspWgt is 0 and 65535.  If the
                mbrSaspWgt is 0, then the converted weight must also be
                0 (the result of the calculation would be 1).  If the 
                mbrSaspWgt is 65535, then the converted weight must be
                the load balancers maximum weight (the result of the
                calculation would be the load balancers maxiumum weight
                plus 1)."
        ::= { slbSaspMemberTableEntry 7 }

slbSaspMemberDefaultWeight              OBJECT-TYPE
        SYNTAX          Unsigned32 ( 0 .. 65535 )
        MAX-ACCESS      read-create
        STATUS          current
        DESCRIPTION
                "The default weight assigned to the member if any
                SASP Agent weight reporting failure occurs.  If there
                is a communication failure or if the
                slbSaspMemberConfidentWeight is false, then the load
                balancer should use this weight as its fallback weight
                when making load balancing decisions."
        DEFVAL          { 1 }
        ::= { slbSaspMemberTableEntry 8 }

slbSaspMemberWeightChanges              OBJECT-TYPE
        SYNTAX          Counter32
        MAX-ACCESS      read-only
        STATUS          current
        DESCRIPTION
                "The total number of times the weight has been modified
                by the SASP Agent."
        ::= { slbSaspMemberTableEntry 9 }

slbSaspMemberLastWeightChange           OBJECT-TYPE
        SYNTAX          DateAndTime
        MAX-ACCESS      read-only
        STATUS          current
        DESCRIPTION
                "Displays the date and time of the last weight change.
                The time that is reported is only local time, so the
                timezone portion of the DateAndTime TC will not be
                specified.  If there have been no reports, the empty
                string is returned."
        ::= { slbSaspMemberTableEntry 10 }

slbSaspMemberRowStatus                  OBJECT-TYPE
        SYNTAX          RowStatus
        MAX-ACCESS      read-create
        STATUS          current
        DESCRIPTION
                "The row status is used by a management station to
                create or delete the row entry in slbSaspMemberTable
                following the RowStatus textual convention."
        ::= { slbSaspMemberTableEntry 11 }


--  *************************************************************
--  *                                                           *
--  * SLB - Server Application State Protocol Stats Table       *
--  *                                                           *
--  *************************************************************

slbSaspStatsTable                      OBJECT-TYPE
        SYNTAX          SEQUENCE OF SlbSaspStatsTableEntry
        MAX-ACCESS      not-accessible
        STATUS          current
        DESCRIPTION
                "A table containing information about the Server
                Application State Protocol Statistics.  Rows are
                created and destroyed when an entry for the 
                slbSaspAgentTable is created or destroy via the
                slbSaspAgentRowStatus."
        ::= { slbSaspStats 1 }

slbSaspStatsTableEntry                 OBJECT-TYPE
        SYNTAX          SlbSaspStatsTableEntry
        MAX-ACCESS      not-accessible
        STATUS          current
        DESCRIPTION
                "Each entry corresponds to a SASP Agent from the
                slbSaspAgentTable.  Each entry contains statistics
                related to the transmitted and received SASP
                messages.  A slbSaspStatsTableEntry cannot exist
                without a corresponding entry in the
                slbSaspAgentTable."
        INDEX   {
                slbEntity,
                slbSaspAgentIpAddressType,
                slbSaspAgentIpAddress,
                slbSaspAgentPort
        }
        ::= { slbSaspStatsTable 1 }

SlbSaspStatsTableEntry ::= SEQUENCE {
        slbSaspStatsTxRegMsgs         Counter32,
        slbSaspStatsTxDeregMsgs       Counter32,
        slbSaspStatsTxGetWeightMsgs   Counter32,
        slbSaspStatsTxSetLBStateMsgs  Counter32,
        slbSaspStatsTxSetMemStateMsgs Counter32,
        slbSaspStatsRxSendWeightMsgs  Counter32,
        slbSaspStatsRxRegMsgs         Counter32,
        slbSaspStatsRxDeregMsgs       Counter32,
        slbSaspStatsRxGetWeightMsgs   Counter32,
        slbSaspStatsRxSetLBStateMsgs  Counter32,
        slbSaspStatsRxSetMemStateMsgs Counter32
}

slbSaspStatsTxRegMsgs                   OBJECT-TYPE
        SYNTAX           Counter32
        MAX-ACCESS       read-only
        STATUS           current
        DESCRIPTION
                "The total number of SASP Registration Requests
                transmitted from the load balancer to the SASP Agent.
                The registration message informs the Agent to start
                reporting the server weight for each member listed in
                the message."
        ::= { slbSaspStatsTableEntry 1 }

slbSaspStatsTxDeregMsgs                 OBJECT-TYPE
        SYNTAX           Counter32
        MAX-ACCESS       read-only
        STATUS           current
        DESCRIPTION
                "The total number of SASP Deregistration Requests
                transmitted from the load balancer to the SASP Agent.
                The deregistration message informs the Agent to stop
                reporting the server weight for each member listed in
                the message."
        ::= { slbSaspStatsTableEntry 2 }

slbSaspStatsTxGetWeightMsgs             OBJECT-TYPE
        SYNTAX           Counter32
        MAX-ACCESS       read-only
        STATUS           current
        DESCRIPTION
               "The total number of SASP Get Weight Requests transmitted
               from the load balancer to the SASP Agent.  The get
               weights message is only used when the load balancer is
               actively retrieving the weight for each member."
        ::= { slbSaspStatsTableEntry 3 }

slbSaspStatsTxSetLBStateMsgs            OBJECT-TYPE
        SYNTAX           Counter32
        MAX-ACCESS       read-only
        STATUS           current
        DESCRIPTION
               "The total number of SASP Set Load Balancer State
               Requests transmitted from the load balancer to the SASP
               Agent.  The message is used to inform the SASP Agent of
               the load balancer's health and its current options."
        ::= { slbSaspStatsTableEntry 4 }

slbSaspStatsTxSetMemStateMsgs           OBJECT-TYPE
        SYNTAX          Counter32
        MAX-ACCESS      read-only
        STATUS          current
        DESCRIPTION
                "The total number of SASP Set Member State Requests
                transmitted from the load balancer to the SASP Agent.
                This message is used to inform the SASP Agent that a
                member has either been activated, or has dropped out
                of service."
        ::= { slbSaspStatsTableEntry 5 }

slbSaspStatsRxSendWeightMsgs            OBJECT-TYPE
        SYNTAX          Counter32
        MAX-ACCESS      read-only
        STATUS          current
        DESCRIPTION
                "The total number of SASP Send Weight Messages received
                from the SASP Agent.  This message is used to update
                the member weights when the load balancer is passively
                retrieving them."
        ::= { slbSaspStatsTableEntry 6 }

slbSaspStatsRxRegMsgs                   OBJECT-TYPE
        SYNTAX          Counter32
        MAX-ACCESS      read-only
        STATUS          current
        DESCRIPTION
                "The total number of SASP Registration Replies received
                from the SASP Agent.  This response indicates whether
                the transmitted registration request was successful, or
                had a failure."
        ::= { slbSaspStatsTableEntry 7 }

slbSaspStatsRxDeregMsgs                 OBJECT-TYPE
        SYNTAX          Counter32
        MAX-ACCESS      read-only
        STATUS          current
        DESCRIPTION
                "The total number of SASP Deregistration Replies
                received from the SASP Agent.  This response indicates
                whether the transmitted request was successful, or had
                a failure."
        ::= { slbSaspStatsTableEntry 8 }

slbSaspStatsRxGetWeightMsgs             OBJECT-TYPE
        SYNTAX          Counter32
        MAX-ACCESS      read-only
        STATUS          current
        DESCRIPTION
                "The total number of SASP Get Weight Replies received
                from the SASP Agent.  This response contains the
                current weights for the requested members.  This
                message is used when the load balancer is actively
                retrieving member weights."
        ::= { slbSaspStatsTableEntry 9 }

slbSaspStatsRxSetLBStateMsgs            OBJECT-TYPE
        SYNTAX          Counter32
        MAX-ACCESS      read-only
        STATUS          current
        DESCRIPTION
                "The total number of SASP Set Load Balancer State
                Replies received from the SASP Agent.  The response
                indicates whether the transmitted request was
                successful, or had a failure."
        ::= { slbSaspStatsTableEntry 10 }

slbSaspStatsRxSetMemStateMsgs           OBJECT-TYPE
        SYNTAX          Counter32
        MAX-ACCESS      read-only
        STATUS          current
        DESCRIPTION
                "The total number of SASP Set Member State Replies
                received from the SASP Agent.  The response indicates
                whether the transmitted request was successful, or had
                a failure."
        ::= { slbSaspStatsTableEntry 11 }


--
-- Notifications
--

ciscoSlbMIBNotificationPrefix OBJECT IDENTIFIER ::=
        {  ciscoSlbMIB 2 }
ciscoSlbMIBNotifications OBJECT IDENTIFIER ::=
        { ciscoSlbMIBNotificationPrefix 0 }

ciscoSlbVirtualStateChange NOTIFICATION-TYPE
        OBJECTS {
                slbVirtualServerState
        }
        STATUS  current
        DESCRIPTION
                "The notification generated when a virtual
                server changes to a new state.  The value of
                slbVirtualServerState indicates the new state."
        ::= { ciscoSlbMIBNotifications 1 }

ciscoSlbRealStateChange NOTIFICATION-TYPE
        OBJECTS {
                slbRealState
        }
        STATUS  current
        DESCRIPTION
                "The notification generated when a real server
                changes to a new state.  The value of
                slbRealServerState indicates the new state."
        ::= { ciscoSlbMIBNotifications 2 }

ciscoSlbSaspStateChange NOTIFICATION-TYPE
        OBJECTS {
                slbSaspEnabled
        }
        STATUS current
        DESCRIPTION
                "The notification generated when the SASP functionality
                has been enabled or disabled on the Load Balancer."
        ::= { ciscoSlbMIBNotifications 3 }

ciscoSlbSaspAgentStateChange NOTIFICATION-TYPE
        OBJECTS {
                slbSaspAgentState
        }
        STATUS current
        DESCRIPTION
                "The notification generated when a SASP Agent changes
                to a new state."
        ::= { ciscoSlbMIBNotifications 4 }

ciscoSlbVServerStateChange NOTIFICATION-TYPE
        OBJECTS {
                slbVServerState,
                slbVServerStateChangeDescr,
                slbVServerClassMap,
                slbVServerPolicyMap
        }
        STATUS  current
        DESCRIPTION
                "The notification generated when a virtual
                server state is changed."
        ::= { ciscoSlbMIBNotifications 5 }

ciscoSlbVServerVIPStateChange NOTIFICATION-TYPE
        OBJECTS {
                slbVServerState,
                slbVServerStateChangeDescr,
                slbVServerClassMap,
                slbVServerPolicyMap,
                slbVServerIpAddressType,
                slbVServerIpAddress,
                slbVServerProtocol
        }
        STATUS  current
        DESCRIPTION
                "The notification generated when configuration
                or association of virtual server IP address(VIP)
                changes."
        ::= { ciscoSlbMIBNotifications 6 }

--
-- Conformance Information
--
ciscoSlbMIBConformance OBJECT IDENTIFIER ::= { ciscoSlbMIB 3 }
ciscoSlbMIBCompliances OBJECT IDENTIFIER ::=
        { ciscoSlbMIBConformance 1 }
ciscoSlbMIBGroups      OBJECT IDENTIFIER ::=
        { ciscoSlbMIBConformance 2 }

-- Compliance

ciscoSlbMIBCompliance MODULE-COMPLIANCE
        STATUS deprecated
        DESCRIPTION
                "The compliance statement for entities which implement
                the Cisco SLB MIB"
        MODULE -- this module
                MANDATORY-GROUPS {
                        ciscoSlbStatsGroup,
                        ciscoSlbDfpPasswordGroup,
                        ciscoSlbServerFarmsGroup,
                        ciscoSlbRealServersGroup,
                        ciscoSlbVirtualServersGroup,
                        ciscoSlbConnectionsGroup,
                        ciscoSlbVirtualClientsGroup,
                        ciscoSlbStickyObjectsGroup,
                        ciscoSlbDfpAgentGroup,
                        ciscoSlbDfpRealGroup,
                        ciscoSlbNotifEnabledGroup
                }

                OBJECT          slbServerFarmNat
                MIN-ACCESS      read-only
                DESCRIPTION     "Write access is not required."

                OBJECT          slbServerFarmNumberOfRealServers
                MIN-ACCESS      read-only
                DESCRIPTION     "Write access is not required."

                OBJECT          slbServerFarmBindId
                MIN-ACCESS      read-only
                DESCRIPTION     "Write access is not required."

                OBJECT          slbServerFarmRowStatus
                MIN-ACCESS      read-only
                DESCRIPTION     "Write access is not required."

                OBJECT          slbRealState
                MIN-ACCESS      read-only
                DESCRIPTION     "Write access is not required."

                OBJECT          slbRealMaxConnections
                MIN-ACCESS      read-only
                DESCRIPTION     "Write access is not required."

                OBJECT          slbRealAdminWeight
                MIN-ACCESS      read-only
                DESCRIPTION     "Write access is not required."

                OBJECT          slbRealReassign
                MIN-ACCESS      read-only
                DESCRIPTION     "Write access is not required."

                OBJECT          slbRealRetryInterval
                MIN-ACCESS      read-only
                DESCRIPTION     "Write access is not required."

                OBJECT          slbRealFailedConnections
                MIN-ACCESS      read-only
                DESCRIPTION     "Write access is not required."

                OBJECT          slbRealFailedClients
                MIN-ACCESS      read-only
                DESCRIPTION     "Write access is not required."

                OBJECT          slbRealRowStatus
                MIN-ACCESS      read-only
                DESCRIPTION     "Write access is not required."

                OBJECT          slbVirtualServerState
                MIN-ACCESS      read-only
                DESCRIPTION     "Write access is not required."

                OBJECT          slbVirtualIpAddress
                MIN-ACCESS      read-only
                DESCRIPTION     "Write access is not required."

                OBJECT          slbVirtualPort
                MIN-ACCESS      read-only
                DESCRIPTION     "Write access is not required."

                OBJECT          slbVirtualProtocol
                MIN-ACCESS      read-only
                DESCRIPTION     "Write access is not required."

                OBJECT          slbVirtualService
                MIN-ACCESS      read-only
                DESCRIPTION     "Write access is not required."

                OBJECT          slbVirtualAdvertise
                MIN-ACCESS      read-only
                DESCRIPTION     "Write access is not required."

                OBJECT          slbVirtualFarmName
                MIN-ACCESS      read-only
                DESCRIPTION     "Write access is not required."

                OBJECT          slbVirtualDelayTimer
                MIN-ACCESS      read-only
                DESCRIPTION     "Write access is not required."

                OBJECT          slbVirtualIdleTimer
                MIN-ACCESS      read-only
                DESCRIPTION     "Write access is not required."

                OBJECT          slbVirtualStickyTimer
                MIN-ACCESS      read-only
                DESCRIPTION     "Write access is not required."

                OBJECT          slbVirtualStickyGroup
                MIN-ACCESS      read-only
                DESCRIPTION     "Write access is not required."

                OBJECT          slbVirtualSynguardCount
                MIN-ACCESS      read-only
                DESCRIPTION     "Write access is not required."

                OBJECT          slbVirtualSynguardPeriod
                MIN-ACCESS      read-only
                DESCRIPTION     "Write access is not required."

                OBJECT          slbVirtualRowStatus
                MIN-ACCESS      read-only
                DESCRIPTION     "Write access is not required."

                OBJECT          slbVirtualClientExclude
                MIN-ACCESS      read-only
                DESCRIPTION     "Write access is not required."

                OBJECT          slbVirtualClientRowStatus
                MIN-ACCESS      read-only
                DESCRIPTION     "Write access is not required."

                OBJECT          slbStickyObjectRealIpAddress
                MIN-ACCESS      read-only
                DESCRIPTION     "Write access is not required."

                OBJECT          slbStickyObjectRowStatus
                MIN-ACCESS      read-only
                DESCRIPTION     "Write access is not required."

                OBJECT          slbDfpPasswordPending
                MIN-ACCESS      read-only
                DESCRIPTION     "Write access is not required."

                OBJECT          slbDfpPasswordTimeout
                MIN-ACCESS      read-only
                DESCRIPTION     "Write access is not required."

                OBJECT          slbDfpPasswordRowStatus
                MIN-ACCESS      read-only
                DESCRIPTION     "Write access is not required."

                OBJECT          slbDfpAgentTimeout
                MIN-ACCESS      read-only
                DESCRIPTION     "Write access is not required."

                OBJECT          slbDfpAgentRetryCount
                MIN-ACCESS      read-only
                DESCRIPTION     "Write access is not required."

                OBJECT          slbDfpAgentInterval
                MIN-ACCESS      read-only
                DESCRIPTION     "Write access is not required."

                OBJECT          slbDfpAgentRowStatus
                MIN-ACCESS      read-only
                DESCRIPTION     "Write access is not required."

                OBJECT          slbDfpRealWeight
                MIN-ACCESS      read-only
                DESCRIPTION     "Write access is not required."

                OBJECT          slbDfpRealRowStatus
                MIN-ACCESS      read-only
                DESCRIPTION     "Write access is not required."

        ::= { ciscoSlbMIBCompliances 1 }

ciscoSlbMIBComplianceRev1 MODULE-COMPLIANCE
        STATUS deprecated
        DESCRIPTION
                "The compliance statement for entities which implement
                the Cisco SLB MIB"
        MODULE -- this module
                MANDATORY-GROUPS {
                        ciscoSlbStatsGroup,
                        ciscoSlbDfpPasswordGroup,
                        ciscoSlbServerFarmsGroup,
                        ciscoSlbRealServersGroup,
                        ciscoSlbVirtualServersGroup,
                        ciscoSlbConnectionsGroup,
                        ciscoSlbVirtualClientsGroup,
                        ciscoSlbStickyObjectsGroup,
                        ciscoSlbDfpAgentGroup,
                        ciscoSlbDfpRealGroup,
                        ciscoSlbNotifEnabledGroup,
                        ciscoSlbNotifGroup
                }

                OBJECT          slbServerFarmNat
                MIN-ACCESS      read-only
                DESCRIPTION     "Write access is not required."

                OBJECT          slbServerFarmNumberOfRealServers
                MIN-ACCESS      read-only
                DESCRIPTION     "Write access is not required."

                OBJECT          slbServerFarmBindId
                MIN-ACCESS      read-only
                DESCRIPTION     "Write access is not required."

                OBJECT          slbServerFarmRowStatus
                MIN-ACCESS      read-only
                DESCRIPTION     "Write access is not required."

                OBJECT          slbRealState
                MIN-ACCESS      read-only
                DESCRIPTION     "Write access is not required."

                OBJECT          slbRealMaxConnections
                MIN-ACCESS      read-only
                DESCRIPTION     "Write access is not required."

                OBJECT          slbRealAdminWeight
                MIN-ACCESS      read-only
                DESCRIPTION     "Write access is not required."

                OBJECT          slbRealReassign
                MIN-ACCESS      read-only
                DESCRIPTION     "Write access is not required."

                OBJECT          slbRealRetryInterval
                MIN-ACCESS      read-only
                DESCRIPTION     "Write access is not required."

                OBJECT          slbRealFailedConnections
                MIN-ACCESS      read-only
                DESCRIPTION     "Write access is not required."

                OBJECT          slbRealFailedClients
                MIN-ACCESS      read-only
                DESCRIPTION     "Write access is not required."

                OBJECT          slbRealRowStatus
                MIN-ACCESS      read-only
                DESCRIPTION     "Write access is not required."

                OBJECT          slbVirtualServerState
                MIN-ACCESS      read-only
                DESCRIPTION     "Write access is not required."

                OBJECT          slbVirtualIpAddress
                MIN-ACCESS      read-only
                DESCRIPTION     "Write access is not required."

                OBJECT          slbVirtualPort
                MIN-ACCESS      read-only
                DESCRIPTION     "Write access is not required."

                OBJECT          slbVirtualProtocol
                MIN-ACCESS      read-only
                DESCRIPTION     "Write access is not required."

                OBJECT          slbVirtualService
                MIN-ACCESS      read-only
                DESCRIPTION     "Write access is not required."

                OBJECT          slbVirtualAdvertise
                MIN-ACCESS      read-only
                DESCRIPTION     "Write access is not required."

                OBJECT          slbVirtualFarmName
                MIN-ACCESS      read-only
                DESCRIPTION     "Write access is not required."

                OBJECT          slbVirtualDelayTimer
                MIN-ACCESS      read-only
                DESCRIPTION     "Write access is not required."

                OBJECT          slbVirtualIdleTimer
                MIN-ACCESS      read-only
                DESCRIPTION     "Write access is not required."

                OBJECT          slbVirtualStickyTimer
                MIN-ACCESS      read-only
                DESCRIPTION     "Write access is not required."

                OBJECT          slbVirtualStickyGroup
                MIN-ACCESS      read-only
                DESCRIPTION     "Write access is not required."

                OBJECT          slbVirtualSynguardCount
                MIN-ACCESS      read-only
                DESCRIPTION     "Write access is not required."

                OBJECT          slbVirtualSynguardPeriod
                MIN-ACCESS      read-only
                DESCRIPTION     "Write access is not required."

                OBJECT          slbVirtualRowStatus
                MIN-ACCESS      read-only
                DESCRIPTION     "Write access is not required."

                OBJECT          slbVirtualClientExclude
                MIN-ACCESS      read-only
                DESCRIPTION     "Write access is not required."

                OBJECT          slbVirtualClientRowStatus
                MIN-ACCESS      read-only
                DESCRIPTION     "Write access is not required."

                OBJECT          slbStickyObjectRealIpAddress
                MIN-ACCESS      read-only
                DESCRIPTION     "Write access is not required."

                OBJECT          slbStickyObjectRowStatus
                MIN-ACCESS      read-only
                DESCRIPTION     "Write access is not required."

                OBJECT          slbDfpPasswordPending
                MIN-ACCESS      read-only
                DESCRIPTION     "Write access is not required."

                OBJECT          slbDfpPasswordTimeout
                MIN-ACCESS      read-only
                DESCRIPTION     "Write access is not required."

                OBJECT          slbDfpPasswordRowStatus
                MIN-ACCESS      read-only
                DESCRIPTION     "Write access is not required."

                OBJECT          slbDfpAgentTimeout
                MIN-ACCESS      read-only
                DESCRIPTION     "Write access is not required."

                OBJECT          slbDfpAgentRetryCount
                MIN-ACCESS      read-only
                DESCRIPTION     "Write access is not required."

                OBJECT          slbDfpAgentInterval
                MIN-ACCESS      read-only
                DESCRIPTION     "Write access is not required."

                OBJECT          slbDfpAgentRowStatus
                MIN-ACCESS      read-only
                DESCRIPTION     "Write access is not required."

                OBJECT          slbDfpRealWeight
                MIN-ACCESS      read-only
                DESCRIPTION     "Write access is not required."

                OBJECT          slbDfpRealRowStatus
                MIN-ACCESS      read-only
                DESCRIPTION     "Write access is not required."

        ::= { ciscoSlbMIBCompliances 2 }

ciscoSlbMIBComplianceRev2 MODULE-COMPLIANCE
        STATUS deprecated -- replaced by ciscoSlbMIBComplianceRev3
        DESCRIPTION
                "The compliance statement for entities which implement
                the Cisco SLB MIB"
        MODULE -- this module
                MANDATORY-GROUPS {
                        ciscoSlbStatsGroup,
                        ciscoSlbDfpPasswordGroup,
                        ciscoSlbServerFarmsGroup,
                        ciscoSlbRealServersGroup,
                        ciscoSlbVirtualServersGroup,
                        ciscoSlbConnectionsGroup,
                        ciscoSlbVirtualClientsGroup,
                        ciscoSlbStickyObjectsGroup,
                        ciscoSlbDfpAgentGroup,
                        ciscoSlbDfpRealGroup,
                        ciscoSlbNotifEnabledGroup,
                        ciscoSlbNotifGroup,
                        ciscoSlbSaspGroup,
                        ciscoSlbSaspAgentGroup,
                        ciscoSlbSaspGroupGroup,
                        ciscoSlbSaspMemberGroup,
                        ciscoSlbSaspStatsGroup,
                        ciscoSlbSaspNotifGroup
                }

                OBJECT          slbServerFarmNat
                MIN-ACCESS      read-only
                DESCRIPTION     "Write access is not required."

                OBJECT          slbServerFarmNumberOfRealServers
                MIN-ACCESS      read-only
                DESCRIPTION     "Write access is not required."

                OBJECT          slbServerFarmBindId
                MIN-ACCESS      read-only
                DESCRIPTION     "Write access is not required."

                OBJECT          slbServerFarmRowStatus
                MIN-ACCESS      read-only
                DESCRIPTION     "Write access is not required."

                OBJECT          slbRealState
                MIN-ACCESS      read-only
                DESCRIPTION     "Write access is not required."

                OBJECT          slbRealMaxConnections
                MIN-ACCESS      read-only
                DESCRIPTION     "Write access is not required."

                OBJECT          slbRealAdminWeight
                MIN-ACCESS      read-only
                DESCRIPTION     "Write access is not required."

                OBJECT          slbRealReassign
                MIN-ACCESS      read-only
                DESCRIPTION     "Write access is not required."

                OBJECT          slbRealRetryInterval
                MIN-ACCESS      read-only
                DESCRIPTION     "Write access is not required."

                OBJECT          slbRealFailedConnections
                MIN-ACCESS      read-only
                DESCRIPTION     "Write access is not required."

                OBJECT          slbRealFailedClients
                MIN-ACCESS      read-only
                DESCRIPTION     "Write access is not required."

                OBJECT          slbRealRowStatus
                MIN-ACCESS      read-only
                DESCRIPTION     "Write access is not required."

                OBJECT          slbVirtualServerState
                MIN-ACCESS      read-only
                DESCRIPTION     "Write access is not required."

                OBJECT          slbVirtualIpAddress
                MIN-ACCESS      read-only
                DESCRIPTION     "Write access is not required."

                OBJECT          slbVirtualPort
                MIN-ACCESS      read-only
                DESCRIPTION     "Write access is not required."

                OBJECT          slbVirtualProtocol
                MIN-ACCESS      read-only
                DESCRIPTION     "Write access is not required."

                OBJECT          slbVirtualService
                MIN-ACCESS      read-only
                DESCRIPTION     "Write access is not required."

                OBJECT          slbVirtualAdvertise
                MIN-ACCESS      read-only
                DESCRIPTION     "Write access is not required."

                OBJECT          slbVirtualFarmName
                MIN-ACCESS      read-only
                DESCRIPTION     "Write access is not required."

                OBJECT          slbVirtualDelayTimer
                MIN-ACCESS      read-only
                DESCRIPTION     "Write access is not required."

                OBJECT          slbVirtualIdleTimer
                MIN-ACCESS      read-only
                DESCRIPTION     "Write access is not required."

                OBJECT          slbVirtualStickyTimer
                MIN-ACCESS      read-only
                DESCRIPTION     "Write access is not required."

                OBJECT          slbVirtualStickyGroup
                MIN-ACCESS      read-only
                DESCRIPTION     "Write access is not required."

                OBJECT          slbVirtualSynguardCount
                MIN-ACCESS      read-only
                DESCRIPTION     "Write access is not required."

                OBJECT          slbVirtualSynguardPeriod
                MIN-ACCESS      read-only
                DESCRIPTION     "Write access is not required."

                OBJECT          slbVirtualRowStatus
                MIN-ACCESS      read-only
                DESCRIPTION     "Write access is not required."

                OBJECT          slbVirtualClientExclude
                MIN-ACCESS      read-only
                DESCRIPTION     "Write access is not required."

                OBJECT          slbVirtualClientRowStatus
                MIN-ACCESS      read-only
                DESCRIPTION     "Write access is not required."

                OBJECT          slbStickyObjectRealIpAddress
                MIN-ACCESS      read-only
                DESCRIPTION     "Write access is not required."

                OBJECT          slbStickyObjectRowStatus
                MIN-ACCESS      read-only
                DESCRIPTION     "Write access is not required."

                OBJECT          slbDfpPasswordPending
                MIN-ACCESS      read-only
                DESCRIPTION     "Write access is not required."

                OBJECT          slbDfpPasswordTimeout
                MIN-ACCESS      read-only
                DESCRIPTION     "Write access is not required."

                OBJECT          slbDfpPasswordRowStatus
                MIN-ACCESS      read-only
                DESCRIPTION     "Write access is not required."

                OBJECT          slbDfpAgentTimeout
                MIN-ACCESS      read-only
                DESCRIPTION     "Write access is not required."

                OBJECT          slbDfpAgentRetryCount
                MIN-ACCESS      read-only
                DESCRIPTION     "Write access is not required."

                OBJECT          slbDfpAgentInterval
                MIN-ACCESS      read-only
                DESCRIPTION     "Write access is not required."

                OBJECT          slbDfpAgentRowStatus
                MIN-ACCESS      read-only
                DESCRIPTION     "Write access is not required."

                OBJECT          slbDfpRealWeight
                MIN-ACCESS      read-only
                DESCRIPTION     "Write access is not required."

                OBJECT          slbDfpRealRowStatus
                MIN-ACCESS      read-only
                DESCRIPTION     "Write access is not required."

        ::= { ciscoSlbMIBCompliances 3 }

ciscoSlbMIBComplianceRev3 MODULE-COMPLIANCE
        STATUS current
        DESCRIPTION
                "The compliance statement for entities which implement
                the Cisco SLB MIB"
        MODULE -- this module
                MANDATORY-GROUPS {
                        ciscoSlbStatsGroup,
                        ciscoSlbDfpPasswordGroup,
                        ciscoSlbServerFarmsGroup,
                        ciscoSlbRealServersGroup,
                        ciscoSlbConnectionsGroup,
                        ciscoSlbStickyObjectsGroup,
                        ciscoSlbDfpAgentGroup,
                        ciscoSlbDfpRealGroup,
                        ciscoSlbNotifEnabledGroup,
                        ciscoSlbNotifGroup,
                        ciscoSlbSaspGroup,
                        ciscoSlbSaspAgentGroup,
                        ciscoSlbSaspGroupGroup,
                        ciscoSlbSaspMemberGroup,
                        ciscoSlbSaspStatsGroup,
                        ciscoSlbSaspNotifGroup
                }


                GROUP   ciscoSlbVirtualServersGroup
                DESCRIPTION
                    "The implmentation of this group is
                    mandatory for those systems where
                    virtual server is identified by 
                    name."

                GROUP ciscoSlbVirtualClientsGroup
                DESCRIPTION
                    "The implmentation of this group is
                    mandatory for those systems where
                    virtual server is identified by 
                    name."

                GROUP   ciscoSlbVServerInfoGroup
                DESCRIPTION
                    "The implmentation of this group is
                    mandatory for those systems where
                    virtual server is identified by
                    vserver identifier."

                GROUP ciscoSlbVServerIPGroup 
                DESCRIPTION
                    "The implmentation of this group is
                    mandatory for those systems where
                    virtual server is identified by
                    vserver identifier."

                GROUP    ciscoSlbVServerNotifEnabledGroup
                DESCRIPTION
                    "The implmentation of this group is
                    mandatory for those systems where
                    virtual server notifications
                    identify virtual server and 
                    virtual servers are associated with
                    class maps and policy maps." 

                GROUP    ciscoSlbVServerNotifGroup
                DESCRIPTION
                    "The implmentation of this group is
                    mandatory for those systems where
                    virtual server is identified by the
                    virtual server identifier."

                OBJECT          slbServerFarmNat
                MIN-ACCESS      read-only
                DESCRIPTION     "Write access is not required."

                OBJECT          slbServerFarmNumberOfRealServers
                MIN-ACCESS      read-only
                DESCRIPTION     "Write access is not required."

                OBJECT          slbServerFarmBindId
                MIN-ACCESS      read-only
                DESCRIPTION     "Write access is not required."

                OBJECT          slbServerFarmRowStatus
                MIN-ACCESS      read-only
                DESCRIPTION     "Write access is not required."

                OBJECT          slbRealState
                MIN-ACCESS      read-only
                DESCRIPTION     "Write access is not required."

                OBJECT          slbRealMaxConnections
                MIN-ACCESS      read-only
                DESCRIPTION     "Write access is not required."

                OBJECT          slbRealAdminWeight
                MIN-ACCESS      read-only
                DESCRIPTION     "Write access is not required."

                OBJECT          slbRealReassign
                MIN-ACCESS      read-only
                DESCRIPTION     "Write access is not required."

                OBJECT          slbRealRetryInterval
                MIN-ACCESS      read-only
                DESCRIPTION     "Write access is not required."

                OBJECT          slbRealFailedConnections
                MIN-ACCESS      read-only
                DESCRIPTION     "Write access is not required."

                OBJECT          slbRealFailedClients
                MIN-ACCESS      read-only
                DESCRIPTION     "Write access is not required."

                OBJECT          slbRealRowStatus
                MIN-ACCESS      read-only
                DESCRIPTION     "Write access is not required."

                OBJECT          slbVirtualServerState
                MIN-ACCESS      read-only
                DESCRIPTION     "Write access is not required."

                OBJECT          slbVirtualIpAddress
                MIN-ACCESS      read-only
                DESCRIPTION     "Write access is not required."

                OBJECT          slbVirtualPort
                MIN-ACCESS      read-only
                DESCRIPTION     "Write access is not required."

                OBJECT          slbVirtualProtocol
                MIN-ACCESS      read-only
                DESCRIPTION     "Write access is not required."

                OBJECT          slbVirtualService
                MIN-ACCESS      read-only
                DESCRIPTION     "Write access is not required."

                OBJECT          slbVirtualAdvertise
                MIN-ACCESS      read-only
                DESCRIPTION     "Write access is not required."

                OBJECT          slbVirtualFarmName
                MIN-ACCESS      read-only
                DESCRIPTION     "Write access is not required."

                OBJECT          slbVirtualDelayTimer
                MIN-ACCESS      read-only
                DESCRIPTION     "Write access is not required."

                OBJECT          slbVirtualIdleTimer
                MIN-ACCESS      read-only
                DESCRIPTION     "Write access is not required."

                OBJECT          slbVirtualStickyTimer
                MIN-ACCESS      read-only
                DESCRIPTION     "Write access is not required."

                OBJECT          slbVirtualStickyGroup
                MIN-ACCESS      read-only
                DESCRIPTION     "Write access is not required."

                OBJECT          slbVirtualSynguardCount
                MIN-ACCESS      read-only
                DESCRIPTION     "Write access is not required."

                OBJECT          slbVirtualSynguardPeriod
                MIN-ACCESS      read-only
                DESCRIPTION     "Write access is not required."

                OBJECT          slbVirtualRowStatus
                MIN-ACCESS      read-only
                DESCRIPTION     "Write access is not required."

                OBJECT          slbVirtualClientExclude
                MIN-ACCESS      read-only
                DESCRIPTION     "Write access is not required."

                OBJECT          slbVirtualClientRowStatus
                MIN-ACCESS      read-only
                DESCRIPTION     "Write access is not required."

                OBJECT          slbStickyObjectRealIpAddress
                MIN-ACCESS      read-only
                DESCRIPTION     "Write access is not required."

                OBJECT          slbStickyObjectRowStatus
                MIN-ACCESS      read-only
                DESCRIPTION     "Write access is not required."

                OBJECT          slbDfpPasswordPending
                MIN-ACCESS      read-only
                DESCRIPTION     "Write access is not required."

                OBJECT          slbDfpPasswordTimeout
                MIN-ACCESS      read-only
                DESCRIPTION     "Write access is not required."

                OBJECT          slbDfpPasswordRowStatus
                MIN-ACCESS      read-only
                DESCRIPTION     "Write access is not required."

                OBJECT          slbDfpAgentTimeout
                MIN-ACCESS      read-only
                DESCRIPTION     "Write access is not required."

                OBJECT          slbDfpAgentRetryCount
                MIN-ACCESS      read-only
                DESCRIPTION     "Write access is not required."

                OBJECT          slbDfpAgentInterval
                MIN-ACCESS      read-only
                DESCRIPTION     "Write access is not required."

                OBJECT          slbDfpAgentRowStatus
                MIN-ACCESS      read-only
                DESCRIPTION     "Write access is not required."

                OBJECT          slbDfpRealWeight
                MIN-ACCESS      read-only
                DESCRIPTION     "Write access is not required."

                OBJECT          slbDfpRealRowStatus
                MIN-ACCESS      read-only
                DESCRIPTION     "Write access is not required."

        ::= { ciscoSlbMIBCompliances 4 }

-- Units of Conformance

ciscoSlbStatsGroup OBJECT-GROUP
        OBJECTS {
                slbStatsUnassistedSwitchingPkts,
                slbStatsUnassistedSwitchingHCPks,
                slbStatsAssistedSwitchingPkts,
                slbStatsAssistedSwitchingHCPkts,
                slbStatsCreatedConnections,
                slbStatsCreatedHCConnections,
                slbStatsEstablishedConnections,
                slbStatsEstablishedHCConnections,
                slbStatsDestroyedConnections,
                slbStatsDestroyedHCConnections,
                slbStatsReassignedConnections,
                slbStatsReassignedHCConnections,
                slbStatsZombies,
                slbStatsHCZombies
        }
        STATUS current
        DESCRIPTION
                "SLB Statistic objects."
        ::= { ciscoSlbMIBGroups 1 }

ciscoSlbServerFarmsGroup  OBJECT-GROUP
        OBJECTS {
                slbServerFarmPredictor,
                slbServerFarmNat,
                slbServerFarmNumberOfRealServers,
                slbServerFarmBindId,
                slbServerFarmRowStatus
        }
        STATUS current
        DESCRIPTION
                "The SLB serverfarm objects."
        ::= { ciscoSlbMIBGroups 2 }

ciscoSlbRealServersGroup  OBJECT-GROUP
        OBJECTS {
                slbRealState,
                slbRealNumberOfConnections,
                slbRealNumberOfDummyConnections,
                slbRealMaxConnections,
                slbRealAdminWeight,
                slbRealOperWeight,
                slbRealMetric,
                slbRealReassign,
                slbRealRetryInterval,
                slbRealFailedConnections,
                slbRealFailedClients,
                slbRealConsecutiveFails,
                slbRealTotalFails,
                slbRealRowStatus,
                slbRealTotalConnections,
                slbRealHCTotalConnections
        }
        STATUS current
        DESCRIPTION
                "The SLB real server objects."
        ::= { ciscoSlbMIBGroups 3 }

ciscoSlbVirtualServersGroup OBJECT-GROUP
        OBJECTS {
                slbVirtualServerState,
                slbVirtualIndex,
                slbVirtualIpAddress,
                slbVirtualPort,
                slbVirtualProtocol,
                slbVirtualService,
                slbVirtualAdvertise,
                slbVirtualFarmName,
                slbVirtualDelayTimer,
                slbVirtualIdleTimer,
                slbVirtualStickyTimer,
                slbVirtualStickyGroup,
                slbVirtualSynguardCount,
                slbVirtualSynguardPeriod,
                slbVirtualRowStatus,
                slbVirtualNumberOfConnections,
                slbVirtualTotalConnections,
                slbVirtualHCTotalConnections
        }
        STATUS current
        DESCRIPTION
                "The SLB virtual server objects."
        ::= { ciscoSlbMIBGroups 4 }

ciscoSlbConnectionsGroup  OBJECT-GROUP
        OBJECTS {
                slbConnectionState,
                slbConnectionRealIpAddr,
                slbConnectionServerPort,
                slbConnectionNumCacheEntries,
                slbConnectionSynCount
        }
        STATUS current
        DESCRIPTION
                "The SLB connection objects."
        ::= { ciscoSlbMIBGroups 5 }

ciscoSlbVirtualClientsGroup  OBJECT-GROUP
        OBJECTS {
                slbVirtualClientExclude,
                slbVirtualClientRowStatus               
        }
        STATUS current
        DESCRIPTION
                "The SLB virtual client objects."
        ::= { ciscoSlbMIBGroups 6 }

ciscoSlbStickyObjectsGroup  OBJECT-GROUP
        OBJECTS {
                slbStickyObjectRealIpAddress,
                slbStickyObjectConnectionCount,
                slbStickyObjectFtpControlCount,
                slbStickyObjectRowStatus
        }
        STATUS current
        DESCRIPTION
                "The SLB sticky objects."
        ::= { ciscoSlbMIBGroups 7 }

ciscoSlbDfpPasswordGroup  OBJECT-GROUP
        OBJECTS {
                slbDfpPasswordPending,
                slbDfpPasswordTimeout,
                slbDfpPasswordRowStatus
        }
        STATUS current
        DESCRIPTION
                "SLB DFP password objects."
        ::= { ciscoSlbMIBGroups 8 }

ciscoSlbDfpAgentGroup  OBJECT-GROUP
        OBJECTS {
                slbDfpAgentState,
                slbDfpAgentTimeout,
                slbDfpAgentRetryCount,
                slbDfpAgentInterval,
                slbDfpAgentRowStatus
        }
        STATUS current
        DESCRIPTION
                "The SLB DFP agent objects."
        ::= { ciscoSlbMIBGroups 9 }

ciscoSlbDfpRealGroup  OBJECT-GROUP
        OBJECTS {
                slbDfpRealWeight,
                slbDfpRealRowStatus
        }
        STATUS current
        DESCRIPTION
                "The SLB DFP real server objects."
        ::= { ciscoSlbMIBGroups 10 }

ciscoSlbNotifEnabledGroup  OBJECT-GROUP
        OBJECTS {
                cSlbVirtStateChangeNotifEnabled,
                cSlbRealStateChangeNotifEnabled
        }
        STATUS current
        DESCRIPTION
                "The SLB Notification Truth Value objects."
        ::= { ciscoSlbMIBGroups 11 }

ciscoSlbVirtualServersAddGroup OBJECT-GROUP
        OBJECTS {
                slbVirtualMask
        }
        STATUS current
        DESCRIPTION
            "A collection of additional SlbVirtualServer objects used to
             further define an Slb virtual server. "
        ::= { ciscoSlbMIBGroups 12 }

ciscoSlbNotifGroup NOTIFICATION-GROUP
        NOTIFICATIONS {
                ciscoSlbVirtualStateChange,
                ciscoSlbRealStateChange
        }
        STATUS current
        DESCRIPTION
            "A collection of objects providing SLB notifications."
        ::= { ciscoSlbMIBGroups 13 }

ciscoSlbSaspGroup  OBJECT-GROUP
        OBJECTS {
                slbSaspIdentifier,
                slbSaspEnabled,
                slbSaspHealth,
                slbSaspRedundancy,
                slbSaspMaxAgents,
                slbSaspMaxLbWeight
        }
        STATUS current
        DESCRIPTION
                "The SLB SASP objects."
        ::= { ciscoSlbMIBGroups 14 }

ciscoSlbSaspAgentGroup  OBJECT-GROUP
        OBJECTS {
                slbSaspAgentLabel,
                slbSaspAgentState,
                slbSaspAgentLastStateChange,
                slbSaspAgentRowStatus
        }
        STATUS current
        DESCRIPTION
                "The SLB SASP Agent objects."
        ::= { ciscoSlbMIBGroups 15 }

ciscoSlbSaspGroupGroup   OBJECT-GROUP
        OBJECTS {
                slbSaspGroupRowStatus
        }
        STATUS current
        DESCRIPTION
                "The SLB SASP Group objects."
        ::= { ciscoSlbMIBGroups 16 }

ciscoSlbSaspMemberGroup  OBJECT-GROUP
        OBJECTS {
                slbSaspMemberSaspWeight,
                slbSaspMemberConfidentWeight,
                slbSaspMemberConvertedWeight,
                slbSaspMemberDefaultWeight,
                slbSaspMemberWeightChanges,
                slbSaspMemberLastWeightChange,
                slbSaspMemberRowStatus
        }
        STATUS current
        DESCRIPTION
                "The SLB SASP Member objects."
        ::= { ciscoSlbMIBGroups 17 }

ciscoSlbSaspStatsGroup  OBJECT-GROUP
        OBJECTS {
                slbSaspStatsTxRegMsgs,
                slbSaspStatsTxDeregMsgs,
                slbSaspStatsTxGetWeightMsgs,
                slbSaspStatsTxSetLBStateMsgs,
                slbSaspStatsTxSetMemStateMsgs,
                slbSaspStatsRxSendWeightMsgs,
                slbSaspStatsRxRegMsgs,
                slbSaspStatsRxDeregMsgs,
                slbSaspStatsRxGetWeightMsgs,
                slbSaspStatsRxSetLBStateMsgs,
                slbSaspStatsRxSetMemStateMsgs
        }
        STATUS current
        DESCRIPTION
                "A collection of objects providing SLB SASP statistics."
        ::= { ciscoSlbMIBGroups 18 }

ciscoSlbSaspNotifGroup NOTIFICATION-GROUP
        NOTIFICATIONS {
                ciscoSlbSaspStateChange,
                ciscoSlbSaspAgentStateChange
        }
        STATUS current
        DESCRIPTION
            "A collection of objects providing SASP notifications."
        ::= { ciscoSlbMIBGroups 19 }

ciscoSlbVServerInfoGroup OBJECT-GROUP
        OBJECTS {
                slbVServerClassMap,
                slbVServerPolicyMap,
                slbVServerState ,
                slbVServerStateChangeDescr,
                slbVServerNumberOfConnections,
                slbVServerTotalConnections
        }
        STATUS current
        DESCRIPTION
                "The list of objects that are applicable to
                virtual server statistics."
        ::= { ciscoSlbMIBGroups 21 }

ciscoSlbVServerIPGroup OBJECT-GROUP
        OBJECTS {
                slbVServerIpAddressType,
                slbVServerIpAddress,
                slbVServerIpMask,
                slbVServerProtocol,
                slbVServerPortLow,
                slbVServerPortHigh,
                slbVServerStorageType,
                slbVServerRowStatus
        }
        STATUS current
        DESCRIPTION
                "The list of objects that are applicable to
                virtual server identified by IP Address/Port."
        ::= { ciscoSlbMIBGroups 22 }

ciscoSlbVServerNotifEnabledGroup  OBJECT-GROUP
        OBJECTS {
                cSlbVServerStateChangeNotifEnabled
        }
        STATUS current
        DESCRIPTION
                "The object used for enabling/disabling
                Virtual Server notifications."
        ::= { ciscoSlbMIBGroups 23 }

ciscoSlbVServerNotifGroup NOTIFICATION-GROUP
        NOTIFICATIONS {
                ciscoSlbVServerStateChange,
                ciscoSlbVServerVIPStateChange
        }
        STATUS current
        DESCRIPTION
            "A collection of objects providing Virtual Server
            notifications."
        ::= { ciscoSlbMIBGroups 24 }

END
