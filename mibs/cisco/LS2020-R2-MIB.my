LIGHTSTREAM-MIB DEFINITIONS ::= BEGIN

          IMPORTS
                     enterprises, IpAddress, Counter, TimeTicks,
		     Gauge
                             FROM RFC1155-SMI
                     mib-2, ifIndex, DisplayString
                             FROM RFC1213-MIB
                     OBJECT-TYPE
                             FROM RFC-1212
                     TRAP-TYPE
                             FROM RFC-1215;

-- $Id: LS2020-R2-MIB.my,v 1.6 2010/11/17 04:38:17 jeneric Exp $ 
--
-- ************************************************************
-- ** NOTICE: These MIB definitions are still in the process **
-- ** of being defined and refined.                          **
-- ** Expect that they will change.                          **
-- ************************************************************
-- 
-- Copyright 1993 LightStream Corporation.  All Rights Reserved.
-- Reproduction of this document is authorized on
-- condition that this copyright notice is included.
-- This LightStream Corp. SNMP Management Information Base Specification
-- (Specification) embodies LightStream Corp.'s
-- proprietary intellectual property.  LightStream Corp. retains all
-- title and ownership in the Specification, including any
-- revisions.  
--
-- This Specification is supplied "AS IS," and LightStream Corp. makes
-- no warranty, either express or implied, as to the use,
-- operation, condition, or performance of the Specification.

-- The formula for determining the ifIndex value for a given interface is
--
--        ((slotNumber * 1000) + portNumber + typeOffset)
--
--	where:
--		slotNumber   An integer between 1 and 11.
--		
--			     For the logical interface used to
--			     represent the ATM network, this value is
--			     always 11.
--			     
--			     For physical interfaces this is the number of
--			     the slot this card resides in starting
--			     with the number 1.
--
--		portNumber   An integer between 0 and 7.
--		
--			     For the logical interface used to
--			     represent the ATM network, this value is
--			     always 4.
--
--			     For a physical interface this is the port
--			     number of the given card.
--
--		typeOffset   This is an arbitrary assigned value.
--
--			     For Ethernet the value is 100.
--			     For FDDI the value is 200.
--			     All other types have a value of 0.

	-- Textual conventions used in this MIB

	   LightStreamStatus ::= INTEGER {
					 enabled(1),
					 disabled(2)
					 }



	   LightStreamValidation ::= INTEGER {
					     valid(1),
					     invalid(2)
					     }


	   LightStreamFilterAction ::= INTEGER {
					       forward(1),
					       block(2)
					       }


	-- Important Object Identifiers for the private MIB
	-- First LightStream's identification in the private enterprise subtree

	lightStream	      OBJECT IDENTIFIER ::= { enterprises 711 }

        lightStreamOIDs       OBJECT IDENTIFIER ::= { lightStream 1 }
	lightStreamProducts   OBJECT IDENTIFIER ::= { lightStream 2 }
	lightStreamInternet   OBJECT IDENTIFIER ::= { lightStream 3 }
        lightStreamVli        OBJECT IDENTIFIER ::= { lightStream 4 }

	lightStreamEOM        OBJECT IDENTIFIER ::= { lightStream 1000 }


-- This subtree is used not for objects but for object identifiers
-- that are required here and there

-- LightStream_ATM is defined in mib.c. This is a placeholder.
   lightStreamATM OBJECT IDENTIFIER ::= { lightStreamOIDs 1 }

--   lsOther is used to define varbinds in trap message    

    	lsOther		 OBJECT IDENTIFIER ::= { lightStreamOIDs 2 }
    	lsTrapNumber	 OBJECT IDENTIFIER ::= { lsOther 1 }
    	lsTrapText	 OBJECT IDENTIFIER ::= { lsOther 2 }
    	lsTrapName       OBJECT IDENTIFIER ::= { lsOther 3 }

-- lsConfig is used to identify conguration internal objects

    	lsConfig         OBJECT IDENTIFIER ::= { lightStreamOIDs 3 }

-- Misc definitions

	LightStreamUpToMaxAge	::= INTEGER (1..3600)
        LightStreamDLCI  ::= INTEGER        -- 0..DLCINumber
    	VCI   ::= INTEGER

--


-- This section is reserved for product specific subtrees. Any
-- product needing a private MIB will be assigned a subtree here

	atmSwitch           OBJECT IDENTIFIER ::= { lightStreamProducts 1 }


--
-- This section is for variables that are associated with the chassis
-- 

         chassisInfo OBJECT IDENTIFIER ::= { atmSwitch 1 }

         chassisId OBJECT-TYPE
               SYNTAX  INTEGER
               ACCESS  read-only
               STATUS  mandatory
               DESCRIPTION
    	 	    	  "Chassis ID (24 bits)"
               ::= { chassisInfo 2 }

         chassisActiveIpAddr OBJECT-TYPE
               SYNTAX  IpAddress
               ACCESS  read-write
               STATUS  mandatory
               DESCRIPTION
    	 	    	  "Active IP Address for Management of this chassis.
                           This is the IP address used for network mangement
                           and will point to the active of the 2 NPs in	
                           a given chassis."
               ::= { chassisInfo 3 }

         chassisSecondaryIpAddr OBJECT-TYPE
               SYNTAX  IpAddress
               ACCESS  read-write
               STATUS  mandatory
               DESCRIPTION
    	 	    	  "Secondary IP Address for Management of this chassis.
                           This is the IP address used for network mangement
                           and will point to the backup NP in a given chassis."
               ::= { chassisInfo 4 }

         chassisNetworkMask OBJECT-TYPE
               SYNTAX  IpAddress
               ACCESS  read-write
               STATUS  mandatory
               DESCRIPTION
    	 	    	  "Subnet mask used for the IP addresses associated
                           with switch ports"
               ::= { chassisInfo 5 }


       chassisEthernetIpAddr OBJECT-TYPE
               SYNTAX IpAddress
               ACCESS read-write
               STATUS mandatory
               DESCRIPTION
                       "This is the IP Address associated with the ethernet
                        port on the primary NP in the chassis.
                        The Ethernet port on the backup NP is unused,should
                        that NP become primary it will take over the
                        chassisEthernetIpAddr."
                ::= { chassisInfo 6 }

       chassisEthernetIpMask  OBJECT-TYPE
               SYNTAX IpAddress
               ACCESS read-write
               STATUS mandatory
               DESCRIPTION
                       "This is the IP network mask associated with the
                        Ethernet to which the network processors in the
                        chassis are connected."
                ::= { chassisInfo 7 }

       chassisDefaultIpRouter  OBJECT-TYPE
               SYNTAX IpAddress
               ACCESS read-write
               STATUS mandatory
               DESCRIPTION
                       "This is a machine, connected to the same ethernet as
                        the chassis' NPs, which is capable of routing
                        IP datagrams to other portions of the Internet."
                ::= { chassisInfo 8 }

       chassisStatusWord  OBJECT-TYPE
               SYNTAX INTEGER
               ACCESS read-only
               STATUS mandatory
               DESCRIPTION
    	    	    "Bit map of certain chassis wide status information
                     for use with UB Net/Director."
 
                ::= { chassisInfo 9 }

       chassisConsoleTrapLevel  OBJECT-TYPE
    	    	SYNTAX INTEGER {
    	    	    	operational   (1),
    	    	    	informational (2),
    	    	    	trace         (3),
    	    	    	debug         (4),
    	    	    	off           (5)
        	    	}
               ACCESS read-only
               STATUS mandatory
               DESCRIPTION
    	    	    "Trap level to use with console trap display"
 
                ::= { chassisInfo 10 }

--
-- 
-- Variables associated with a card
-- 

         cardInfo OBJECT IDENTIFIER ::= { atmSwitch 2 }

         cardTable OBJECT-TYPE
    	    SYNTAX  SEQUENCE OF CardEntry
            ACCESS  not-accessible
	    STATUS  mandatory
    	    DESCRIPTION
                "Card specific information"
	    ::= { cardInfo 1 }

	 cardEntry OBJECT-TYPE
	    SYNTAX   CardEntry
	    ACCESS   not-accessible
	    STATUS   mandatory
	    DESCRIPTION
	        "An entry in the chassis card table. (1-n)"
	    INDEX   { cardIndex }
	    ::= { cardTable 1 }

	 CardEntry ::=
	    SEQUENCE {
	        cardIndex
	        	INTEGER,
	        cardName
	        	DisplayString (SIZE (0..255)),
    	        cardBoardType
	        	DisplayString (SIZE (0..255)),
	        cardLcSoftwareVersion
	        	DisplayString (SIZE (0..255)),
	        cardLccSoftwareVersion
	        	DisplayString (SIZE (0..255)),
    	    	cardPID
                        INTEGER,
		cardMaxVCs 
			INTEGER,
    	    	cardOperStatus
                        INTEGER,
    	    	cardAdminStatus
    	    	    	INTEGER,
    	    	cardStatusWord
                        INTEGER,
    	    	cardConfigRegister
                        INTEGER
	        }
    	        	    
         cardIndex OBJECT-TYPE
              SYNTAX  INTEGER
    	      ACCESS  read-only
              STATUS  mandatory
              DESCRIPTION
                  "Unique Index consisting of card number."
          ::= { cardEntry 1 }

         cardName OBJECT-TYPE
              SYNTAX  DisplayString (SIZE (0..255))
              ACCESS  read-write
              STATUS  mandatory
              DESCRIPTION
    	        	  "Name of Card"
              ::= { cardEntry 2 }

         cardBoardType OBJECT-TYPE
              SYNTAX  DisplayString (SIZE (0..255))
    	      ACCESS  read-only
              STATUS  mandatory
              DESCRIPTION
                  "Board type of this card."
          ::= { cardEntry 3 }


         cardLcSoftwareVersion OBJECT-TYPE
              SYNTAX  DisplayString (SIZE (0..255))
    	      ACCESS  read-only
              STATUS  mandatory
              DESCRIPTION
                  "Software revision of process running in the line card"
              ::= { cardEntry 4 }

         cardLccSoftwareVersion OBJECT-TYPE
              SYNTAX  DisplayString (SIZE (0..255))
    	      ACCESS  read-only
              STATUS  mandatory
              DESCRIPTION
                  "Software revision of process controlling card"
              ::= { cardEntry 5 }

         cardPID OBJECT-TYPE
              SYNTAX  INTEGER
    	      ACCESS  read-only
              STATUS  mandatory
              DESCRIPTION
                  "Unique Process ID for LCC process (from OS)."
          ::= { cardEntry 6 }

         cardMaxVCs OBJECT-TYPE
              SYNTAX  INTEGER 
    	      ACCESS  read-write
              STATUS  mandatory
              DESCRIPTION
                  "Maximum Virtual Circuits Supported by this card"
           DEFVAL   { 800 }
          ::= { cardEntry 7 }

         cardOperStatus OBJECT-TYPE
              SYNTAX  INTEGER {
    	    	    up (1),
    	    	    down (2),
    	    	    testing (3),
                    empty (4)
    	    	    }
    	      ACCESS  read-only
              STATUS  mandatory
              DESCRIPTION
                  "Card Operational status"
          ::= { cardEntry 8 }

         cardAdminStatus OBJECT-TYPE
              SYNTAX  INTEGER {
    	    	    up (1),
    	    	    down (2),
    	    	    testing (3)
    	    	    }
    	      ACCESS  read-write
              STATUS  mandatory
              DESCRIPTION
                  "Administratively Desired Status of this card"
          ::= { cardEntry 9 }

         cardStatusWord OBJECT-TYPE
              SYNTAX  INTEGER
              ACCESS  read-only
              STATUS  mandatory
              DESCRIPTION
                  "Card status word, for use with the UB
                   Net/Director product"
          ::= { cardEntry 10 }

         cardConfigRegister OBJECT-TYPE
              SYNTAX  INTEGER {
    	    	    up (1),
    	    	    down (2),
    	    	    testing (3),
                    empty (4)
    	    	    }
    	      ACCESS  read-only
              STATUS  mandatory
              DESCRIPTION
                  "Actual Card Enable Status as read from status register"
          ::= { cardEntry 11 }


--
-- 
-- This section contains objects that are extension to the
-- Interface tables for Edge Ports
-- for admin and oper status use ifOperStatus and ifAdminStatus
--
-- -------------------------------------------------------------

         portInfo OBJECT IDENTIFIER ::= { atmSwitch 3 }

         portInfoTable OBJECT-TYPE
    	    SYNTAX  SEQUENCE OF PortInfoEntry
            ACCESS  not-accessible
	    STATUS  mandatory
	    DESCRIPTION
                "Port specific information"
	    ::= { portInfo 1 }

	 portInfoEntry OBJECT-TYPE
	    SYNTAX   PortInfoEntry
	    ACCESS   not-accessible
	    STATUS   mandatory
	    DESCRIPTION
	        "An entry in the Edge Port table."
	    INDEX   { portInfoIndex }
	    ::= { portInfoTable 1 }

	 PortInfoEntry ::=
	    SEQUENCE {
	        portInfoIndex
	        	INTEGER,
    	    	portInfoType
    	    	    	INTEGER,
    	    	portInfoSpecific
                        OBJECT IDENTIFIER,
    	    	portInfoName
                        DisplayString,
    	    	portInfoErrorLimit
    	    	    	INTEGER
	        }
    	        	    
         portInfoIndex OBJECT-TYPE
              SYNTAX  INTEGER
    	      ACCESS  read-only
              STATUS  mandatory
              DESCRIPTION
                  "This is the ifIndex value of the corresponding
		  ifEntry.  See comments above."
              ::= { portInfoEntry 1 }

         portInfoType OBJECT-TYPE
              SYNTAX  INTEGER {
    	    	    empty (1),
    	    	    error (2),
    	    	    unknown (3),
    	    	    switch (4),
    	    	    np (5),
    	    	    lsEdge (6),
    	    	    lsTrunk (7),
    	    	    msTrunk (8),
    	    	    msEdge (10),
		    plc12fac1 (11),  			-- 2-port FDDI
		    plc18eac1 (12),  			--  8-port Ethernet
		    plc1Lstoken (13),			-- Token Ring
		    plc18sac1Edge (14),		-- 8-port Low-speed serial edge
		    plc18sac1Trunk (15),		-- 8-port Low-speed Serial trunk
		    clc1Gen (30),			-- Generic CLC1	
		    clc12oc3ac1Edge (31),		-- 2-port OC3 edge 
		    clc12oc3ac1Trunk (32),		-- 2-port OC3 trunk 
		    clc18t3ac1Edge (33),		-- 8-port T3/E3 edge 
		    clc18t3ac1Trunk (34),		-- 8-port T3/E3 trunk 
		    clc12taxiac1Edge (35),		-- 2-port 155 Mbit TAXI edge 
		    clc12taxiac1Trunk (36),		-- 2-port 155 Mbit TAXI trunk 
		    clc18t1e1cbrac1 (37)		-- 8-port Constant Bit Rate edge 
    	    	    }
    	      ACCESS  read-only
              STATUS  mandatory
              DESCRIPTION
    	    	    "Object id of the port information table
    	    	     used with this port. (e.g. ls1InfoTable
                     for the low speed line card version 1"
              ::= { portInfoEntry 2 }

         portInfoSpecific OBJECT-TYPE
              SYNTAX  OBJECT IDENTIFIER
    	      ACCESS  read-only
              STATUS  mandatory
              DESCRIPTION
    	    	    "Object id of the port information table
    	    	     used with this port. (e.g. ls1InfoTable
                     for the low speed line card version 1"
              ::= { portInfoEntry 3 }

         portInfoName OBJECT-TYPE
              SYNTAX  DisplayString
    	      ACCESS  read-write
              STATUS  mandatory
              DESCRIPTION
    	    	    "The name of this port. This is primary
                     used as a help aid to identification.
                     There is no absolute need for it to be set."
              ::= { portInfoEntry 4 }


         portInfoErrorLimit OBJECT-TYPE
              SYNTAX  INTEGER
    	      ACCESS  read-write
              STATUS  mandatory
              DESCRIPTION
    	    	    "The maximum error for this port, expressed as an inverse
		     power of ten.  I.E. 3 sets an acceptable error rate of
		     10**-3 receive+transmit errors.

		     When this object is set to the value 0, the error
		     limit trap is disabled.  This value is always 0,
		     i.e. disabled for Ethernet and FDDI ports."
              ::= { portInfoEntry 5 }


--
-- This group contains a set of tables, one table for each board
-- type. An object-identifier in the port table points to the
-- appropriate table for the port.

-- Note: Several MIB II interface variables are used as is and
-- not duplicated here.


         portTransmission OBJECT IDENTIFIER ::= { atmSwitch 4 }

-- -------------------------------------------------------------
-- LS1 (T1 card) port information table
-- -------------------------------------------------------------

         ls1InfoTable OBJECT-TYPE
    	    SYNTAX  SEQUENCE OF Ls1InfoEntry

            ACCESS  not-accessible
	    STATUS  mandatory
	    DESCRIPTION
                "Edge Port Address table specific Information"
	    ::= { portTransmission 1 }

	 ls1InfoEntry OBJECT-TYPE
	    SYNTAX   Ls1InfoEntry
	    ACCESS   not-accessible
	    STATUS   mandatory
	    DESCRIPTION
	        "An entry in the Edge Port Address table."
	    INDEX   { ls1InfoIfIndex }
	    ::= { ls1InfoTable 1 }

	 Ls1InfoEntry ::=
	    SEQUENCE {
	        ls1InfoIfIndex
	        	INTEGER,
    	    	ls1InfoType
                        INTEGER,
		ls1InfoOperCsuType
			INTEGER,
		ls1InfoAdminCsuType
			INTEGER,
    	        ls1InfoOperXmitBaudRate
    	        	INTEGER,
    	        ls1InfoAdminXmitBaudRate
    	        	INTEGER,
    	        ls1InfoOperRcvBaudRate
    	        	INTEGER,
    	        ls1InfoAdminRcvBaudRate
    	        	INTEGER,
		ls1InfoOperNetIntType
			INTEGER,
		ls1InfoAdminNetIntType
			INTEGER,
		ls1InfoOperModemState
			INTEGER,
		ls1InfoOperProtocol
    	    	    	INTEGER,
		ls1InfoAdminProtocol
			INTEGER,
		ls1InfoOperControlBandwidthSize
			INTEGER,
		ls1InfoAdminControlBandwidthSize
			INTEGER,
		ls1InfoOperDataBandwidthSize
			INTEGER,
		ls1InfoAdminDataBandwidthSize
			INTEGER,
		ls1InfoOperLoopMode 
			INTEGER,
		ls1InfoAdminLoopMode
			INTEGER,
		ls1InfoLcAutoEnable 
			INTEGER,
		ls1InfoLcDebugLevel 
			INTEGER,
		ls1InfoDataCellCapacity
			INTEGER,
		ls1InfoDataCellAvailable
			INTEGER,
		ls1InfoMeasuredBaudRate
			INTEGER,
		ls1InfoLinkUtilization
			INTEGER,
		ls1InfoAdminOperTrigger
			INTEGER
	        }
    	        	    
        ls1InfoIfIndex OBJECT-TYPE
              SYNTAX  INTEGER
    	      ACCESS  read-only
              STATUS  mandatory
              DESCRIPTION
                  "This is the ifIndex value of the corresponding
		  ifEntry.  See comments above."
              ::= { ls1InfoEntry 1 }

         ls1InfoType OBJECT-TYPE
              SYNTAX  INTEGER {
                        v35   (1),
			rs422 (2),
			rs530 (3),
    	    	    	t1    (4),
			unknown (99)   -- this usually means a problem with the faintail
			}
    	      ACCESS  read-only
              STATUS  mandatory
              DESCRIPTION
                  "Level 1 interface type used for this port"
              ::= { ls1InfoEntry 2 }

         ls1InfoOperCsuType   OBJECT-TYPE
              SYNTAX  INTEGER {
    	    	    none (1),
    	    	    larse (2)
                    }
    	      ACCESS  read-only
              STATUS  mandatory
              DESCRIPTION
                  "Identifier of operational CSU Interface"
              ::= { ls1InfoEntry 3 }

         ls1InfoAdminCsuType   OBJECT-TYPE
              SYNTAX  INTEGER {
    	    	    none (1),
    	    	    larse (2)
                    }
    	      ACCESS  read-write
              STATUS  mandatory
              DESCRIPTION
                  "Identifier of administartively specified  CSU Interface"
              ::= { ls1InfoEntry 4 }

         ls1InfoOperRcvBaudRate   OBJECT-TYPE
              SYNTAX  INTEGER
    	      ACCESS  read-only
              STATUS  mandatory
              DESCRIPTION
    	    	    "Operation receive baud rate"
              ::= { ls1InfoEntry 5 }

         ls1InfoAdminRcvBaudRate   OBJECT-TYPE
              SYNTAX  INTEGER
    	      ACCESS  read-write
              STATUS  mandatory
              DESCRIPTION
    	    	    "Adminsitratively desired receive baud rate"
              ::= { ls1InfoEntry 6 }

         ls1InfoOperXmitBaudRate   OBJECT-TYPE
              SYNTAX  INTEGER
    	      ACCESS  read-only
              STATUS  mandatory
              DESCRIPTION
    	    	    "Operation transmit baud rate."
              ::= { ls1InfoEntry 7 }

         ls1InfoAdminXmitBaudRate   OBJECT-TYPE
              SYNTAX  INTEGER
    	      ACCESS  read-write
              STATUS  mandatory
              DESCRIPTION
                  "Admistratively desired transmission baud rate"
              ::= { ls1InfoEntry 8 }

         ls1InfoOperNetIntType   OBJECT-TYPE
              SYNTAX  INTEGER {
			dce (1),
			dte (2),
			dceTTloop (3) -- DCE with local tt clock loopback
			}
    	      ACCESS  read-only
              STATUS  mandatory
              DESCRIPTION
                  "Operational network Interface Type for this port:
    	    	   DCE, DTE, or DCE with local tt loopback.  This last
		   option provides the ability to interface to DTE
		   devices which are unable to return the tt signal
		   as required for full V.35 standard compliance."
              ::= { ls1InfoEntry 9 }

         ls1InfoAdminNetIntType   OBJECT-TYPE
              SYNTAX  INTEGER {
			dce (1),
			dte (2),
			dceTTloop (3) -- DCE with local tt clock loopback
			}
    	      ACCESS  read-write
              STATUS  mandatory
              DESCRIPTION
                  "Administrative or desired Network Interface Type for 
    	    	   DCE, DTE, or DCE with local tt loopback.  This last
		   option provides the ability to interface to DTE
		   devices which are unable to return the tt signal
		   as required for full V.35 standard compliance."
              ::= { ls1InfoEntry 10 }

         ls1InfoOperModemState   OBJECT-TYPE
              SYNTAX  INTEGER
    	      ACCESS  read-only
              STATUS  mandatory
              DESCRIPTION
                  "Operational Status of certain modem signals.  A bitmask
		   which gives the current state of certain modmem signals
		   is returned.  If the Port is configured as a DTE, bit 0
		   will be DCD and bit 1 DSR.  If the Port is configured as
		   a DCE, bit 0 will be RTS and bit 1 DTR."
              ::= { ls1InfoEntry 13 }


         ls1InfoOperProtocol   OBJECT-TYPE
              SYNTAX  INTEGER {
			trunk (1),
			frameRelay (2),
			frameForwarding (3),
			ppp (4),
    	    	    	unknown (5)
			}
    	      ACCESS  read-only
              STATUS  mandatory
              DESCRIPTION
                  "Operational higher level protocol stack to support
		   on this port."
              ::= { ls1InfoEntry 15 }

         ls1InfoAdminProtocol   OBJECT-TYPE
              SYNTAX  INTEGER {
			trunk (1),
			frameRelay (2),
			frameForwarding (3),
			ppp (4),
    	    	    	unknown (5)
			}
    	      ACCESS  read-write
              STATUS  mandatory
              DESCRIPTION
                  "Administratively desired higher level protocol stack 
    	    	    to support on this port."
              ::= { ls1InfoEntry 16 }

         ls1InfoOperControlBandwidthSize   OBJECT-TYPE
              SYNTAX  INTEGER
    	      ACCESS  read-only
              STATUS  mandatory
              DESCRIPTION
    	    	    "The current operation value of the control bandwidth
                     size for this port.  This is a scaling factor.  This
		     value is multiplied by ls1InfoOperRcvBaudRate and the
		     result divided by 1000 to derive the actual bandwidth."
              ::= { ls1InfoEntry 21 }

         ls1InfoAdminControlBandwidthSize   OBJECT-TYPE
              SYNTAX  INTEGER
    	      ACCESS  read-write
              STATUS  mandatory
              DESCRIPTION
    	    	    "The current administratively desired value of the
    	    	     control bandwidth size for this port. Setting the
    	    	     trigger variable ls1InfoAdimOperTrigger will cause
         	     this value to become the operation value. 
		     This is a scaling factor.  This value is multiplied
		     by ls1InfoAdminRcvBaudRate and the result divided by
		     1000 to derive the actual bandwidth."
              ::= { ls1InfoEntry 22 }

         ls1InfoOperDataBandwidthSize   OBJECT-TYPE
              SYNTAX  INTEGER
    	      ACCESS  read-only
              STATUS  mandatory
              DESCRIPTION
    	    	    "The current operation value of the data bandwidth
                     size for this port.  This is a scaling factor.  This
		     value is multiplied by ls1InfoOperRcvBaudRate and the
		     result divided by 1000 to derive the actual bandwidth."
              ::= { ls1InfoEntry 23 }

         ls1InfoAdminDataBandwidthSize   OBJECT-TYPE
              SYNTAX  INTEGER
    	      ACCESS  read-write
              STATUS  mandatory
              DESCRIPTION
    	    	    "The current administratively desired value of the
    	    	     data bandwidth size for this port. Setting the
    	    	     trigger variable ls1InfoAdimOperTrigger will cause
         	     this value to become the operation value.
		     This is a scaling factor.  This value is multiplied
		     by ls1InfoAdminRcvBaudRate and the result divided by
		     1000 to derive the actual bandwidth."
              ::= { ls1InfoEntry 24 }

         ls1InfoOperLoopMode   OBJECT-TYPE
              SYNTAX  INTEGER {
			none (1),
			internal (2),
			external (3),
			remote (4)
			}
    	      ACCESS  read-only
              STATUS  mandatory
              DESCRIPTION
                  "Operational loop mode for this port:
    	    	   none, internal, external, or remote"
              ::= { ls1InfoEntry 25 }

         ls1InfoAdminLoopMode   OBJECT-TYPE
              SYNTAX  INTEGER {
			none (1),
			internal (2),
			external (3),
			remote (4)
			}
    	      ACCESS  read-write
              STATUS  mandatory
              DESCRIPTION
                  "Administrative or desired loop mode for this
    	    	    port: none, internal, external, or remote"
              ::= { ls1InfoEntry 26 }


	 ls1InfoLcAutoEnable   OBJECT-TYPE
              SYNTAX  INTEGER {
			enabled (1),
			disabled (2)
			}
    	      ACCESS  read-only
              STATUS  mandatory
              DESCRIPTION
                  "State of the LC auto-enable flag for this port.  If
		   enabled the port will be enable at LC boot time.  
		   If disabled the port will remain disabled until
		   configured and started by the LCC software on the NP.
	           This parameter is set in the LC EEPROM by portctl."
              ::= { ls1InfoEntry 27 }

	 ls1InfoLcDebugLevel   OBJECT-TYPE
              SYNTAX  INTEGER
    	      ACCESS  read-only
              STATUS  mandatory
              DESCRIPTION
                  "Value of the LC debug level variable for this port.
	           This parameter is set in the LC EEPROM by portctl."
              ::= { ls1InfoEntry 28 }


	ls1InfoDataCellCapacity   OBJECT-TYPE
              SYNTAX  INTEGER
    	      ACCESS  read-only
              STATUS  mandatory
              DESCRIPTION
                  "The portion of this port's capacity in cells that
		   is allocated for data traffic."
              ::= { ls1InfoEntry 29 }


	 ls1InfoDataCellAvailable   OBJECT-TYPE
              SYNTAX  INTEGER
    	      ACCESS  read-only
              STATUS  mandatory
              DESCRIPTION
                  "The portion of this port's capacity in cells that
		   is available for data traffic.  This variable 
		   is adjusted for the bandwidth consumed by VCs 
		   created using this port.  It does not count VCs
		   which have been configured but not yet established."
              ::= { ls1InfoEntry 30}



         ls1InfoMeasuredBaudRate   OBJECT-TYPE
              SYNTAX  INTEGER
    	      ACCESS  read-only
              STATUS  mandatory
              DESCRIPTION
                  "This is the line rate as measured from the line card."
              ::= { ls1InfoEntry 31}

         ls1InfoLinkUtilization   OBJECT-TYPE
              SYNTAX  INTEGER
    	      ACCESS  read-only
              STATUS  mandatory
              DESCRIPTION
                  "This is an estimated utilization on the link."
              ::= { ls1InfoEntry 32}



         ls1InfoAdminOperTrigger   OBJECT-TYPE
              SYNTAX  INTEGER {
			trigger	 (1),
			other (99)
			}
    	      ACCESS  read-write
              STATUS  mandatory
              DESCRIPTION
    	    	    "When proper commands written to this variable the
    	    	     LCC attempts to change the state of the port such
    	    	     that the oper status reflects the desired admin status."
              ::= { ls1InfoEntry 99 }



--
-- 
-- MS1 (t3 card) port information table 
-- 

         ms1InfoTable OBJECT-TYPE
    	    SYNTAX  SEQUENCE OF Ms1InfoEntry
            ACCESS  not-accessible
	    STATUS  mandatory
	    DESCRIPTION
                "Edge Port Address table specific Information"
	    ::= { portTransmission 2 }

	 ms1InfoEntry OBJECT-TYPE
	    SYNTAX   Ms1InfoEntry
	    ACCESS   not-accessible
	    STATUS   mandatory
	    DESCRIPTION
	        "An entry in the Edge Port Address table."
	    INDEX   { ms1InfoIfIndex }
	    ::= { ms1InfoTable 1 }

	 Ms1InfoEntry ::=
	    SEQUENCE {
	        ms1InfoIfIndex
	        	INTEGER,
    	    	ms1InfoOperCableLength
                        INTEGER,
    	    	ms1InfoAdminCableLength
                        INTEGER,
		ms1InfoOperControlBandwidthSize
			INTEGER,
		ms1InfoAdminControlBandwidthSize
			INTEGER,
		ms1InfoOperDataBandwidthSize
			INTEGER,
		ms1InfoAdminDataBandwidthSize
			INTEGER,

		ms1InfoLcAutoEnable 
			INTEGER,
		ms1InfoLcDebugLevel 
			INTEGER,

		ms1InfoOperProtocol
    	    	    	INTEGER,
		ms1InfoAdminProtocol
			INTEGER,
    	    	ms1InfoOperScramble
                        INTEGER,
    	    	ms1InfoAdminScramble
                        INTEGER,

		ms1InfoDataCellCapacity
			INTEGER,
		ms1InfoDataCellAvailable
			INTEGER,

		ms1InfoLinkUtilization
			INTEGER,

		ms1InfoOperFraming
    	    	    	INTEGER,
--		ms1InfoAdminFraming
--			INTEGER,

		ms1InfoAdminOperTrigger
			INTEGER
	        }
    	        	    
        ms1InfoIfIndex OBJECT-TYPE
              SYNTAX  INTEGER
    	      ACCESS  read-only
              STATUS  mandatory
              DESCRIPTION
                  "This is the ifIndex value of the corresponding
		  ifEntry.  See comments above."
              ::= { ms1InfoEntry 1 }

          ms1InfoOperCableLength OBJECT-TYPE
              SYNTAX  INTEGER {
			t3CableLength1 (1),	--  0 to 450 feet
			t3CableLength2 (2),	--450 to 900 feet
			e3CableLength1 (3),	--  0 to 400 feet
			e3CableLength2 (4),	--300 to 1000 feet
			e3CableLength3 (5),	--800 to 1300 feet
			e3CableLength4 (6)	--1100 to 1900 feet
			}
    	      ACCESS  read-only
              STATUS  mandatory
              DESCRIPTION
                  "Operational value for Cable Length used for this port."
              ::= { ms1InfoEntry 2 }

         ms1InfoAdminCableLength OBJECT-TYPE
              SYNTAX  INTEGER {
			t3CableLength1 (1),	--  0 to 450 feet
			t3CableLength2 (2),	--450 to 900 feet
			e3CableLength1 (3),	--  0 to 400 feet
			e3CableLength2 (4),	--300 to 1000 feet
			e3CableLength3 (5),	--800 to 1300 feet
			e3CableLength4 (6)	--1100 to 1900 feet
			}
    	      ACCESS  read-write
              STATUS  mandatory
              DESCRIPTION
                  "Administrative value for Cable Length used for
		   this port.  Setting the trigger variable 
		   ms1InfoAdimOperTrigger will cause this value
		   to become the operation value. "
              ::= { ms1InfoEntry 3 }


         ms1InfoOperProtocol   OBJECT-TYPE
              SYNTAX  INTEGER {
			trunk (1),
			atmUni (2),
    	    	    	unknown (3)
			}
    	      ACCESS  read-only
              STATUS  mandatory
              DESCRIPTION
                  "Operational higher level protocol stack to support
		   on this port."
              ::= { ms1InfoEntry 4 }

         ms1InfoAdminProtocol   OBJECT-TYPE
              SYNTAX  INTEGER {
			trunk (1),
			atmUni (2),
    	    	    	unknown (3)
			}
    	      ACCESS  read-write
              STATUS  mandatory
              DESCRIPTION
                  "Administratively desired higher level protocol stack 
    	    	    to support on this port."
              ::= { ms1InfoEntry 5 }

         ms1InfoOperControlBandwidthSize   OBJECT-TYPE
              SYNTAX  INTEGER
    	      ACCESS  read-only
              STATUS  mandatory
              DESCRIPTION
    	    	    "The current operation value of the control bandwidth
                     size for this port.  This is a scaling factor.  This
		     value is multiplied by ms1InfoOperRcvBaudRate and the
		     result divided by 1000 to derive the actual bandwidth."
              ::= { ms1InfoEntry 10 }

         ms1InfoAdminControlBandwidthSize   OBJECT-TYPE
              SYNTAX  INTEGER
    	      ACCESS  read-write
              STATUS  mandatory
              DESCRIPTION
    	    	    "The current administratively desired value of the
    	    	     control bandwidth size for this port. Setting the
    	    	     trigger variable ms1InfoAdimOperTrigger will cause
         	     this value to become the operation value. 
		     This is a scaling factor.  This value is multiplied
		     by ms1InfoAdminRcvBaudRate and the result divided by
		     1000 to derive the actual bandwidth."
              ::= { ms1InfoEntry 11 }

         ms1InfoOperDataBandwidthSize   OBJECT-TYPE
              SYNTAX  INTEGER
    	      ACCESS  read-only
              STATUS  mandatory
              DESCRIPTION
    	    	    "The current operation value of the data bandwidth
                     size for this port.  This is a scaling factor.  This
		     value is multiplied by ms1InfoOperRcvBaudRate and the
		     result divided by 1000 to derive the actual bandwidth."
              ::= { ms1InfoEntry 12 }

         ms1InfoAdminDataBandwidthSize   OBJECT-TYPE
              SYNTAX  INTEGER
    	      ACCESS  read-write
              STATUS  mandatory
              DESCRIPTION
    	    	    "The current administratively desired value of the
    	    	     data bandwidth size for this port. Setting the
    	    	     trigger variable ms1InfoAdimOperTrigger will cause
         	     this value to become the operation value.
		     This is a scaling factor.  This value is multiplied
		     by ms1InfoAdminRcvBaudRate and the result divided by
		     1000 to derive the actual bandwidth."
              ::= { ms1InfoEntry 13 }



	 ms1InfoLcAutoEnable   OBJECT-TYPE
              SYNTAX  INTEGER {
			enabled (1),
			disabled (2)
			}
    	      ACCESS  read-only
              STATUS  mandatory
              DESCRIPTION
                  "State of the LC auto-enable flag for this port.  If
		   enabled the port will be enable at LC boot time.  
		   If disabled the port will remain disabled until
		   configured and started by the LCC software on the NP.
	           This parameter is set in the LC EEPROM by portctl."
              ::= { ms1InfoEntry 14 }

	 ms1InfoLcDebugLevel   OBJECT-TYPE
              SYNTAX  INTEGER
    	      ACCESS  read-only
              STATUS  mandatory
              DESCRIPTION
                  "Value of the LC debug level variable for this port.
	           This parameter is set in the LC EEPROM by portctl."
              ::= { ms1InfoEntry 15 }

          ms1InfoOperScramble OBJECT-TYPE
              SYNTAX  INTEGER {
			t3ScrambleEnable (1),	--  Enable Cell Payload Scrambling
       			t3ScrambleDisable (2)	-- Disable Cell Payload Scrambling
			}
    	      ACCESS  read-only
              STATUS  mandatory
              DESCRIPTION
                  "Operational value for Cell Payload scrambling used
		  for this port." 
              ::= { ms1InfoEntry 16 }

         ms1InfoAdminScramble OBJECT-TYPE
              SYNTAX  INTEGER {
			t3ScrambleEnable (1),	--  Enable Cell Payload Scrambling
       			t3ScrambleDisable (2)	-- Disable Cell Payload Scrambling
			}
    	      ACCESS  read-write
              STATUS  mandatory
              DESCRIPTION
                  "Administrative value for Cell Payload scrambling used for
		   this port.  Setting the trigger variable 
		   ms1InfoAdimOperTrigger will cause this value
		   to become the operation value. "
              ::= { ms1InfoEntry 17 }


	ms1InfoDataCellCapacity   OBJECT-TYPE
              SYNTAX  INTEGER
    	      ACCESS  read-only
              STATUS  mandatory
              DESCRIPTION
                  "The portion of this port's capacity in cells that
		   is allocated for data traffic."
              ::= { ms1InfoEntry 18 }


	 ms1InfoDataCellAvailable   OBJECT-TYPE
              SYNTAX  INTEGER
    	      ACCESS  read-only
              STATUS  mandatory
              DESCRIPTION
                  "The portion of this port's capacity in cells that
		   is available for data traffic.  This variable 
		   is adjusted for the bandwidth consumed by VCs 
		   created using this port.  It does not count VCs
		   which have been configured but not yet established."
              ::= { ms1InfoEntry 19}

         ms1InfoLinkUtilization   OBJECT-TYPE
              SYNTAX  INTEGER
    	      ACCESS  read-only
              STATUS  mandatory
              DESCRIPTION
                  "This is an estimated utilization on the link."
              ::= { ms1InfoEntry 20 }


         ms1InfoOperFraming   OBJECT-TYPE
              SYNTAX  INTEGER {
			plcp (1),
			t3-Hec (2),
    	    	    	g-804 (3)
			}
    	      ACCESS  read-only
              STATUS  mandatory
              DESCRIPTION
                  "Operational ATM framing typein use on this port."
              ::= { ms1InfoEntry 21 }

          ms1InfoAdminOperTrigger   OBJECT-TYPE
              SYNTAX  INTEGER {
			trigger	 (1),
			other (99)
			}
    	      ACCESS  read-write
              STATUS  mandatory
              DESCRIPTION
    	    	    "When proper commands written to this variable the
    	    	     LCC attempts to change the state of the port such
    	    	     that the oper status reflects the desired admin status."
              ::= { ms1InfoEntry 99 }


--

--
-- NP port information table
--

         npInfoTable OBJECT-TYPE
    	    SYNTAX  SEQUENCE OF NpInfoEntry
            ACCESS  not-accessible
	    STATUS  mandatory
	    DESCRIPTION
                "Edge Port Address table specific Information"
	    ::= { portTransmission 3 }

	 npInfoEntry OBJECT-TYPE
	    SYNTAX   NpInfoEntry
	    ACCESS   not-accessible
	    STATUS   mandatory
	    DESCRIPTION
	        "An entry in the NP configuration table."
	    INDEX   { npInfoIfIndex }
	    ::= { npInfoTable 1 }

	 NpInfoEntry ::=
	    SEQUENCE {
	        npInfoIfIndex
	        	INTEGER,
		npInfoIPCommittedRate
			INTEGER,
		npInfoIPCommittedBurst
			INTEGER,
		npInfoIPExcessRate
			INTEGER,
		npInfoIPExcessBurst
			INTEGER,
		npInfoIPNCircuits 
			INTEGER,
		npInfoAdminOperTrigger
			INTEGER
	        }
    	        	    
        npInfoIfIndex OBJECT-TYPE
              SYNTAX  INTEGER
    	      ACCESS  read-only
              STATUS  mandatory
              DESCRIPTION
                  "This is the ifIndex value of the corresponding
		  ifEntry.  See comments above."
              ::= { npInfoEntry 1 }

	npInfoIPCommittedRate OBJECT-TYPE
		SYNTAX INTEGER
		ACCESS read-write
		STATUS mandatory
		DESCRIPTION
		    "Default committed rate for IP circuits"
		::= { npInfoEntry 5 }

	npInfoIPCommittedBurst OBJECT-TYPE
		SYNTAX INTEGER
		ACCESS read-write
		STATUS mandatory
		DESCRIPTION
		    "Default committed burst rate for IP circuits"
		::= { npInfoEntry 6 }

	npInfoIPExcessRate OBJECT-TYPE
		SYNTAX INTEGER
		ACCESS read-write
		STATUS mandatory
		DESCRIPTION
		    "Default excess rate for IP circuits"
		::= { npInfoEntry 7 }

	npInfoIPExcessBurst OBJECT-TYPE
		SYNTAX INTEGER
		ACCESS read-write
		STATUS mandatory
		DESCRIPTION
		    "Default excess burst rate for IP circuits"
		::= { npInfoEntry 8 }

	npInfoIPNCircuits OBJECT-TYPE
		SYNTAX INTEGER
		ACCESS read-write
		STATUS mandatory
		DESCRIPTION
		    "Number of IP circuits supported"
		::= { npInfoEntry 9 }

         npInfoAdminOperTrigger   OBJECT-TYPE
              SYNTAX  INTEGER {
			trigger	(1),
			other (99)
			}
    	      ACCESS  read-write
              STATUS  mandatory
              DESCRIPTION
    	    	    "When proper commands written to this variable the
    	    	     LCC attempts to change the state of the port such
    	    	     that the oper status reflects the desired admin status."
              ::= { npInfoEntry 99 }

--
-- 
-- CLC1 (ASIC Cell Line Card) port information table 
-- 

         clc1InfoTable OBJECT-TYPE
    	    SYNTAX  SEQUENCE OF Clc1InfoEntry
            ACCESS  not-accessible
	    STATUS  mandatory
	    DESCRIPTION
                "Edge Port Address table specific Information"
	    ::= { portTransmission 4 }

	 clc1InfoEntry OBJECT-TYPE
	    SYNTAX   Clc1InfoEntry
	    ACCESS   not-accessible
	    STATUS   mandatory
	    DESCRIPTION
	        "An entry in the Edge Port Address table."
	    INDEX   { clc1InfoIfIndex }
	    ::= { clc1InfoTable 1 }

	 Clc1InfoEntry ::=
	    SEQUENCE {
	        clc1InfoIfIndex
	        	INTEGER,
		clc1InfoOperControlBandwidthSize
			INTEGER,
		clc1InfoAdminControlBandwidthSize
			INTEGER,
		clc1InfoOperDataBandwidthSize
			INTEGER,
		clc1InfoAdminDataBandwidthSize
			INTEGER,

		clc1InfoOperLoopMode 
			INTEGER,
		clc1InfoAdminLoopMode
			INTEGER,

		clc1InfoLcAutoEnable 
			INTEGER,
		clc1InfoLcDebugLevel 
			INTEGER,

		clc1InfoOperProtocol
    	    	    	INTEGER,
		clc1InfoAdminProtocol
			INTEGER,
    	    	clc1InfoOperScramble
                        INTEGER,
    	    	clc1InfoAdminScramble
                        INTEGER,

		clc1InfoDataCellCapacity
			INTEGER,
		clc1InfoDataCellAvailable
			INTEGER,

		clc1InfoLinkUtilization
			INTEGER,
		clc1InfoOperClock
			INTEGER,
		clc1InfoAdminClock
			INTEGER,

		clc1InfoAdminOperTrigger
			INTEGER
	        }
    	        	    
        clc1InfoIfIndex OBJECT-TYPE
              SYNTAX  INTEGER
    	      ACCESS  read-only
              STATUS  mandatory
              DESCRIPTION
                  "This is the ifIndex value of the corresponding
		  ifEntry.  See comments above."
              ::= { clc1InfoEntry 1 }


         clc1InfoOperProtocol   OBJECT-TYPE
              SYNTAX  INTEGER {
			trunk (1),
			atmUni (2),
    	    	    	unknown (3)
			}
    	      ACCESS  read-only
              STATUS  mandatory
              DESCRIPTION
                  "Operational higher level protocol stack to support
		   on this port."
              ::= { clc1InfoEntry 4 }

         clc1InfoAdminProtocol   OBJECT-TYPE
              SYNTAX  INTEGER {
			trunk (1),
			atmUni (2),
    	    	    	unknown (3)
			}
    	      ACCESS  read-write
              STATUS  mandatory
              DESCRIPTION
                  "Administratively desired higher level protocol stack 
    	    	    to support on this port."
              ::= { clc1InfoEntry 5 }

         clc1InfoOperLoopMode   OBJECT-TYPE
              SYNTAX  INTEGER {
			none (1),
			internal (2),
			external (3)
			}
    	      ACCESS  read-only
              STATUS  mandatory
              DESCRIPTION
                  "Operational loop mode for this port:
    	    	   none, internal, or external."
              ::= { clc1InfoEntry 6 }

         clc1InfoAdminLoopMode   OBJECT-TYPE
              SYNTAX  INTEGER {
			none (1),
			internal (2),
			external (3)
			}
    	      ACCESS  read-write
              STATUS  mandatory
              DESCRIPTION
                  "Administrative or desired loop mode for this
    	    	    port: none, internal, or external."
              ::= { clc1InfoEntry 7 }



         clc1InfoOperControlBandwidthSize   OBJECT-TYPE
              SYNTAX  INTEGER
    	      ACCESS  read-only
              STATUS  mandatory
              DESCRIPTION
    	    	    "The current operation value of the control bandwidth
                     size for this port.  This is a scaling factor.  This
		     value is multiplied by the port bit rate and the
		     result divided by 1000 to derive the actual bandwidth."
              ::= { clc1InfoEntry 10 }

         clc1InfoAdminControlBandwidthSize   OBJECT-TYPE
              SYNTAX  INTEGER
    	      ACCESS  read-write
              STATUS  mandatory
              DESCRIPTION
    	    	    "The current administratively desired value of the
    	    	     control bandwidth size for this port. Setting the
    	    	     trigger variable clc1InfoAdimOperTrigger will cause
         	     this value to become the operation value. 
		     This is a scaling factor.  This value is multiplied
		     by the port bit rate and the result divided by
		     1000 to derive the actual bandwidth."
              ::= { clc1InfoEntry 11 }

         clc1InfoOperDataBandwidthSize   OBJECT-TYPE
              SYNTAX  INTEGER
    	      ACCESS  read-only
              STATUS  mandatory
              DESCRIPTION
    	    	    "The current operation value of the data bandwidth
                     size for this port.  This is a scaling factor.  This
		     value is multiplied by the port bit rate and the
		     result divided by 1000 to derive the actual bandwidth."
              ::= { clc1InfoEntry 12 }

         clc1InfoAdminDataBandwidthSize   OBJECT-TYPE
              SYNTAX  INTEGER
    	      ACCESS  read-write
              STATUS  mandatory
              DESCRIPTION
    	    	    "The current administratively desired value of the
    	    	     data bandwidth size for this port. Setting the
    	    	     trigger variable clc1InfoAdimOperTrigger will cause
         	     this value to become the operation value.
		     This is a scaling factor.  This value is multiplied
		     by the port bit rate and the result divided by
		     1000 to derive the actual bandwidth."
              ::= { clc1InfoEntry 13 }



	 clc1InfoLcAutoEnable   OBJECT-TYPE
              SYNTAX  INTEGER {
			enabled (1),
			disabled (2)
			}
    	      ACCESS  read-only
              STATUS  mandatory
              DESCRIPTION
                  "State of the LC auto-enable flag for this port.  If
		   enabled the port will be enable at LC boot time.  
		   If disabled the port will remain disabled until
		   configured and started by the LCC software on the NP.
	           This parameter is set in the LC EEPROM by portctl."
              ::= { clc1InfoEntry 14 }

	 clc1InfoLcDebugLevel   OBJECT-TYPE
              SYNTAX  INTEGER
    	      ACCESS  read-only
              STATUS  mandatory
              DESCRIPTION
                  "Value of the LC debug level variable for this port.
	           This parameter is set in the LC EEPROM by portctl."
              ::= { clc1InfoEntry 15 }

          clc1InfoOperScramble OBJECT-TYPE
              SYNTAX  INTEGER {
			scrambleEnable (1),	--  Enable Cell Payload Scrambling
       			scrambleDisable (2)	-- Disable Cell Payload Scrambling
			}
    	      ACCESS  read-only
              STATUS  mandatory
              DESCRIPTION
                  "Operational value for Cell Payload scrambling used
		  for this port." 
              ::= { clc1InfoEntry 16 }

         clc1InfoAdminScramble OBJECT-TYPE
              SYNTAX  INTEGER {
			scrambleEnable (1),	--  Enable Cell Payload Scrambling
       			scrambleDisable (2)	-- Disable Cell Payload Scrambling
			}
    	      ACCESS  read-write
              STATUS  mandatory
              DESCRIPTION
                  "Administrative value for Cell Payload scrambling used for
		   this port.  Setting the trigger variable 
		   clc1InfoAdimOperTrigger will cause this value
		   to become the operation value. "
              ::= { clc1InfoEntry 17 }


	clc1InfoDataCellCapacity   OBJECT-TYPE
              SYNTAX  INTEGER
    	      ACCESS  read-only
              STATUS  mandatory
              DESCRIPTION
                  "The portion of this port's capacity in cells that
		   is allocated for data traffic."
              ::= { clc1InfoEntry 18 }


	 clc1InfoDataCellAvailable   OBJECT-TYPE
              SYNTAX  INTEGER
    	      ACCESS  read-only
              STATUS  mandatory
              DESCRIPTION
                  "The portion of this port's capacity in cells that
		   is available for data traffic.  This variable 
		   is adjusted for the bandwidth consumed by VCs 
		   created using this port.  It does not count VCs
		   which have been configured but not yet established."
              ::= { clc1InfoEntry 19}

         clc1InfoLinkUtilization   OBJECT-TYPE
              SYNTAX  INTEGER
    	      ACCESS  read-only
              STATUS  mandatory
              DESCRIPTION
                  "This is an estimated utilization on the link."
              ::= { clc1InfoEntry 20 }

          clc1InfoOperClock OBJECT-TYPE
              SYNTAX  INTEGER {
			internalClock (1),
       			externalClock (2)
			}
    	      ACCESS  read-only
              STATUS  mandatory
              DESCRIPTION
                  "Operational value for the source of transmit clock for this port."
              ::= { clc1InfoEntry 21 }

         clc1InfoAdminClock OBJECT-TYPE
              SYNTAX  INTEGER {
			internalClock (1),
       			externalClock (2)
			}
    	      ACCESS  read-write
              STATUS  mandatory
              DESCRIPTION
                  "Administrative value for the source of transmit clock 
		   used for this port.  Setting the trigger variable 
		   clc1InfoAdimOperTrigger will cause this value to
		   become the operation value. "
              ::= { clc1InfoEntry 22 }



          clc1InfoAdminOperTrigger   OBJECT-TYPE
              SYNTAX  INTEGER {
			trigger	 (1),
			other (99)
			}
    	      ACCESS  read-write
              STATUS  mandatory
              DESCRIPTION
    	    	    "When proper commands written to this variable the
    	    	     LCC attempts to change the state of the port such
    	    	     that the oper status reflects the desired admin status."
              ::= { clc1InfoEntry 99 }

-- ------------------------------------------------------------------
-- OC3 (Sonet/OC3 Acess Card) port information table 
-- ------------------------------------------------------------------

         oc3InfoTable OBJECT-TYPE
    	    SYNTAX  SEQUENCE OF Oc3InfoEntry
            ACCESS  not-accessible
	    STATUS  mandatory
	    DESCRIPTION
                "Edge Port Address table specific Information"
	    ::= { portTransmission 5 }

	 oc3InfoEntry OBJECT-TYPE
	    SYNTAX   Oc3InfoEntry
	    ACCESS   not-accessible
	    STATUS   mandatory
	    DESCRIPTION
	        "An entry in the Edge Port Address table."
	    INDEX   { ifIndex }
	    ::= { oc3InfoTable 1 }

	 Oc3InfoEntry ::=
	    SEQUENCE {
		oc3InfoReceiveSignalDetect
			INTEGER,
		oc3InfoTransmitSafetySwitch
			INTEGER,
		oc3InfoMediumType
			INTEGER
	}

	 oc3InfoReceiveSignalDetect   OBJECT-TYPE
              SYNTAX  INTEGER {
			active (1),  -- RX signal present.
			inactive (2)  -- RX signal absent.
			}
    	      ACCESS  read-only
              STATUS  mandatory
              DESCRIPTION
                  "This value indicates that a receive signal has
		   been detected on thei port"
              ::= { oc3InfoEntry 1 }

	 oc3InfoTransmitSafetySwitch   OBJECT-TYPE
              SYNTAX  INTEGER {
			enabled (1),  -- saftey on - laser inoperative
			disabled (2)  -- saftey off - laser operative
			}
    	      ACCESS  read-only
              STATUS  mandatory
              DESCRIPTION
                  "State of the Safety Switch with the single mode 
		   interface.  When the saftey switch is enabled, the
		   laser is disabled.  This variable is undefined
		   for multimode interfaces."
              ::= { oc3InfoEntry 2 }

	 oc3InfoMediumType   OBJECT-TYPE
	    SYNTAX  INTEGER {
		    sonet(1),
		    sdh(2)
	            }
	    ACCESS  read-write
	    STATUS  mandatory
	    DESCRIPTION
	           "This variable identifies whether a SONET
	            or a SDH signal is used across this interface."
              ::= { oc3InfoEntry 3 }
--
--
-- Congestion Avoidance Variables
--

         congestionAvoidance OBJECT IDENTIFIER ::= { atmSwitch 5 }

    	 caMaxIntervalPermitLimit OBJECT-TYPE
    	    	SYNTAX INTEGER
    	    	ACCESS read-write
    	    	STATUS mandatory
    	    	DESCRIPTION
    	    	    "The maximum interval at which permit limits
    	    	     are to be reported by trunk and outgoing
    	    	     edge cards."
    	    	::= { congestionAvoidance 1 }
    
    	 caMinIntervalPermitLimit OBJECT-TYPE
    	    	SYNTAX INTEGER
    	    	ACCESS read-write
    	    	STATUS mandatory
    	    	DESCRIPTION
    	    	    "The minimum interval at which permit limits
    	    	     are to be reported by trunk and outgoing
    	    	     edge cards."
    	    	::= { congestionAvoidance 2 }
    
    	 caMinIntervalCaInfo OBJECT-TYPE
    	    	SYNTAX INTEGER
    	    	ACCESS read-write
    	    	STATUS mandatory
    	    	DESCRIPTION
    	    	    "The minimum interval at which CA information
    	    	     processes are to distribute aggregated CA updates
    	    	     to input edge cards."
    	    	::= { congestionAvoidance 3 }
    

--
--
-- These variables are MMA private. That is, they are variables
-- that are used to control or configure the MMA
--

         mmaInfo OBJECT IDENTIFIER ::= { atmSwitch 6 }

    	 mmaDbActive OBJECT-TYPE
    	    	SYNTAX INTEGER {
    	    	    inactive (1),
    	    	    newDBactive (2)
    	    	    }
    	    	ACCESS read-write
    	    	STATUS mandatory
    	    	DESCRIPTION
    	    	    "Controls and displays state of persistent
    	    	     database used by MMA. Primary use of this
    	    	     variable was to allow release 1 configuration
		     systems to shut off the database before it was
		     replaced with a new one and then re-activated.

		     The release 2 configuration mechanism depends on
		     mmaSetLock to backup and coordinate
		     configuration updates."
    	    	::= { mmaInfo 1 }

    	mmaTrapFilter OBJECT-TYPE
    	    	SYNTAX INTEGER {
    	    	    	operational (1),
    	    	    	informational (2),
    	    	    	trace (3),
    	    	    	debug  (4)
        	    	}
    	    	ACCESS read-write
    	    	STATUS mandatory
    	    	DESCRIPTION
    	    	    "Value of highest priority trap that will be
    	    	     be forwarded to any NMS sites. For example
    	    	     if set to mediumPriority then mediumPrioriy
    	    	     and highPriority messages will be forwarded"

    	    	::= { mmaInfo 2 }
    	

    	mmaTrapLanguage OBJECT-TYPE
    	    	SYNTAX INTEGER {
    	    	    	english (1)
--    	    	    	german (2),
--    	    	    	french (3),
--    	    	    	spanish  (4),
--    	    	    	italian (5)
        	    	}
    	    	ACCESS read-write
    	    	STATUS mandatory
    	    	DESCRIPTION
    	    	    "Langauage to be used for the text of traps."
    	    	::= { mmaInfo 3 }
    	
    	mmaCollectionSpace OBJECT-TYPE
    	    	SYNTAX INTEGER
    	    	ACCESS read-write
    	    	STATUS mandatory
    	    	DESCRIPTION
    	    	    "Max size of disk space available for collecting
    	    	     autonomous traps. Actual size is
    	    	     mmaCollectionSpace * 1024"
    	    	::= { mmaInfo 4 }
    	
    	mmaConfigHost OBJECT-TYPE
    	    	SYNTAX OCTET STRING (SIZE(0..255))
    	    	ACCESS read-write
    	    	STATUS mandatory
    	    	DESCRIPTION
    	    	    "Host supplying configuration file"
    	    	::= { mmaInfo 5 }

    	mmaConfigAuthor OBJECT-TYPE
    	    	SYNTAX OCTET STRING (SIZE(0..255))
    	    	ACCESS read-write
    	    	STATUS mandatory
    	    	DESCRIPTION
    	    	    "Person who last changed configuration file"
    	    	::= { mmaInfo 6 }

    	mmaConfigID OBJECT-TYPE
    	    	SYNTAX INTEGER
    	    	ACCESS read-write
    	    	STATUS mandatory
    	    	DESCRIPTION
    	    	    "Configuration ID set by configuration program"
    	    	::= { mmaInfo 7 }

       	mmaSetLock OBJECT-TYPE
    	    	SYNTAX INTEGER {
    	    	    	unlock(1),
    	    	    	lockVolatile(2),
			lockPermanent(3)
    	    	    	}
    	    	ACCESS read-write
    	    	STATUS mandatory
    	    	DESCRIPTION
    	    	    "If a user locks this field (2 or 3), set commands
		    are accepted only from that IP address.  The lock
		    times out if the session is idle for two minutes.

		    There are two configuration files: mma.db.pag and
		    mma.db.dir.  If set to lockPermanent(3), these
		    files are copied to mma.db.BAK.pag and
		    mma.db.BAK.dir, and sets are written to the
		    configuration files.  Otherwise sets are written
		    to run-time memory only.  To recover backup
		    configuration files, the user must log in to the
		    LightStream node and rename the files."
    	    	::= { mmaInfo 8 }

    	mmaPID OBJECT-TYPE
    	    	SYNTAX INTEGER
    	    	ACCESS read-only
    	    	STATUS mandatory
    	    	DESCRIPTION
    	    	    "PID of the MMA process"
    	    	::= { mmaInfo 9 }

    	mmaTrapLog OBJECT-TYPE
    	    	SYNTAX INTEGER {
    	    	    	enabled (1),
                        disabled(2)
                        }
    	    	ACCESS read-write
    	    	STATUS mandatory
    	    	DESCRIPTION
    	    	    "Trap log control field. If enabled the MMA will
                     log traps received from LWMA clients to disk. It
                     saves traps into a 'circular file' such that only
                     the last number of traps are on disk."
    	    	::= { mmaInfo 10 }
    
--
--   The next few variables control the trap interface
--   Users Please Note: Watch for races and take precautions
--

       	mmaTrapNumber OBJECT-TYPE
    	    	SYNTAX INTEGER
    	    	ACCESS read-write
    	    	STATUS mandatory
    	    	DESCRIPTION
    	    	    "Trap Number used by the state and action variables"
    	    	::= { mmaInfo 13 }

    	mmaTrapOnOffState OBJECT-TYPE
    	    	SYNTAX INTEGER {
    	    	    	trapOn(1),
    	    	    	trapOff(2),
			trapEnable(3),
			trapDisable(4)
    	    	    	}
    	    	ACCESS read-write
    	    	STATUS mandatory
    	    	DESCRIPTION
    	    	    "On/Off State of Trap specified in mmaTrapNumber
    	    	     and mmaTrapPidSelector"
    	    	::= { mmaInfo 14 }

--
-- Table that map chassis IDs to chassis names in the network
--

         mmaNumNameTable OBJECT-TYPE
    	    SYNTAX  SEQUENCE OF MmaNumNameEntry
            ACCESS  not-accessible
	    STATUS  mandatory
	    DESCRIPTION
                "Table of current file transfers"
	    ::= { mmaInfo 16 }

	 mmaNumNameEntry OBJECT-TYPE
	    SYNTAX   MmaNumNameEntry
	    ACCESS   not-accessible
	    STATUS   mandatory
	    DESCRIPTION
	        "An entry in the file transfer table."
	    INDEX   { mmaNumNameNumber }
	    ::= { mmaNumNameTable 1 }

	 MmaNumNameEntry ::=
	    SEQUENCE {
	        mmaNumNameNumber
	        	INTEGER,
	        mmaNumName
	        	DisplayString
	        }
    	        	    
         mmaNumNameNumber OBJECT-TYPE
              SYNTAX  INTEGER
    	      ACCESS  read-only
              STATUS  mandatory
              DESCRIPTION
                  "Unique Index consisting of chassis ID."
          ::= { mmaNumNameEntry 1 }

         mmaNumName OBJECT-TYPE
              SYNTAX  DisplayString
    	      ACCESS  read-only
              STATUS  mandatory
              DESCRIPTION
                  "Name of chassis corresponding to value of mmaNumNameNumber."
          ::= { mmaNumNameEntry 2 }

    	mmaLwmpTimeouts OBJECT-TYPE
    	    	SYNTAX Counter
    	    	ACCESS read-only
    	    	STATUS mandatory
    	    	DESCRIPTION
    	    	    "The number of times the MMA did a read on a
		    socket to a chassis-resident process and timed out
		    before the process responded.

		    This object is being added here for debug purposes
		    and may be changed in future releases of the MIB."
    	    	::= { mmaInfo 20 }

--
--
-- Collection Variables
--

         collectInfo OBJECT IDENTIFIER ::= { atmSwitch 7 }

         collectTable OBJECT-TYPE
    	    SYNTAX  SEQUENCE OF CollectEntry
            ACCESS  not-accessible
	    STATUS  mandatory
	    DESCRIPTION
                "Collector table of current collections"
	    ::= { collectInfo 1 }

	 collectEntry OBJECT-TYPE
	    SYNTAX   CollectEntry
	    ACCESS   not-accessible
	    STATUS   mandatory
	    DESCRIPTION
	        "An entry in the Collector collection table. (1-n)"
	    INDEX   { collectIndex }
	    ::= { collectTable 1 }

	 CollectEntry ::=
	    SEQUENCE {
	        collectIndex
	        	INTEGER,
	        collectStatus
	        	INTEGER,
    	    	collectStart
    	    	    	INTEGER,
    	    	collectFinish
    	    	    	INTEGER,
	        collectInterval
    	    	    	INTEGER,
	        collectFileName
	        	DisplayString (SIZE (0..255)),
    	    	collectFileSize
    	    	    	INTEGER,
    	    	collectOperStatus
    	    	    	INTEGER
	        }
    	        	    
         collectIndex OBJECT-TYPE
              SYNTAX  INTEGER
    	      ACCESS  read-only
              STATUS  mandatory
              DESCRIPTION
                  "Unique Index consisting of collection number."
          ::= { collectEntry 1 }

         collectStatus OBJECT-TYPE
              SYNTAX  INTEGER {
    	    	    	valid (1),
    	    	    	createRequest (2),
    	    	    	underCreation(3),
    	    	    	invalid(4)
    	    	    	}
    	      ACCESS  read-write
              STATUS  mandatory
              DESCRIPTION
                  "Collection status of this collection row entry."
          ::= { collectEntry 2 }

         collectStart OBJECT-TYPE
              SYNTAX  INTEGER
    	      ACCESS  read-write
              STATUS  mandatory
              DESCRIPTION
                  "Collection start time. If specified and status is
                   valid means a collection will start at time. Time is
                   the UNIX real time in seconds."
          ::= { collectEntry 3 }

         collectFinish OBJECT-TYPE
              SYNTAX  INTEGER
    	      ACCESS  read-write
              STATUS  mandatory
              DESCRIPTION
                  "Collection finish time in TOD seconds."
          ::= { collectEntry 4 }

         collectInterval OBJECT-TYPE
              SYNTAX  INTEGER
    	      ACCESS  read-write
              STATUS  mandatory
              DESCRIPTION
                  "Collection Interval, in seconds."
          ::= { collectEntry 5 }

         collectFileName OBJECT-TYPE
              SYNTAX  DisplayString (SIZE (0..255))
              ACCESS  read-only
              STATUS  mandatory
              DESCRIPTION
    	    	    "Automatically generated filename for this
                     collection. The file name is 'Collect.n' where
    	    	     'n' is the collectIndex."
              ::= { collectEntry 6 }

         collectFileSize OBJECT-TYPE
              SYNTAX  INTEGER
    	      ACCESS  read-write
              STATUS  mandatory
              DESCRIPTION
                  "Max Size of the circular file named in
    	    	   collectFileName. Actual maximum size of file is
    	    	   value of collectFileSize * 1024."
          ::= { collectEntry 7 }

         collectOperStatus OBJECT-TYPE
              SYNTAX  INTEGER {
    	     	    	waiting (1),
    	    	    	running (2),
    	    	    	underCreation(3)
    	    	    	}
    	      ACCESS  read-write
              STATUS  mandatory
              DESCRIPTION
                  "Collection status of this collection row entry."
          ::= { collectEntry 8 }

         collectDataBase OBJECT-TYPE
    	    SYNTAX  SEQUENCE OF CollectDbEntry
            ACCESS  not-accessible
	    STATUS  mandatory
	    DESCRIPTION
                "Collector table of current collections"
	    ::= { collectInfo 2 }

	 collectDbEntry OBJECT-TYPE
	    SYNTAX   CollectDbEntry
	    ACCESS   not-accessible
	    STATUS   mandatory
	    DESCRIPTION
	        "An entry in the Collector group database. (1-n)"
	    INDEX   { collectDBIndex, collectDBInstance }
	    ::= { collectDataBase 1 }

	 CollectDbEntry ::=
	    SEQUENCE {
    	        collectDBIndex
	        	INTEGER,
	        collectDBInstance
	        	INTEGER,
    	        collectDBObjectID
    	        	OBJECT IDENTIFIER,
    	    	collectDBStatus
    	    	    	INTEGER
	        }
    	        	    
         collectDBIndex OBJECT-TYPE
              SYNTAX  INTEGER
    	      ACCESS  read-only
              STATUS  mandatory
              DESCRIPTION
                  "Unique Index equal to collectIndex"
          ::= { collectDbEntry 1 }

         collectDBInstance OBJECT-TYPE
              SYNTAX  INTEGER
    	      ACCESS  read-only
              STATUS  mandatory
              DESCRIPTION
                  "Record instance within a group ID"
          ::= { collectDbEntry 2 }

    	 collectDBObjectID OBJECT-TYPE
    	      SYNTAX  OBJECT IDENTIFIER
    	      ACCESS  read-write
    	      STATUS  mandatory
    	      DESCRIPTION
    	    	    "Object identifier of a member of a group
    	    	     specified by the group ID and instance."
    	      ::= { collectDbEntry 3 }

         collectDBStatus OBJECT-TYPE
              SYNTAX  INTEGER {
    	    	    	valid (1),
    	    	    	createRequest (2),
    	    	    	underCreation(3),
    	    	    	invalid(4)
    	    	    	}
    	      ACCESS  read-write
              STATUS  mandatory
              DESCRIPTION
                  "Collection status of this collection database
                   row entry."
          ::= { collectDbEntry 4 }

         collectCommunityName OBJECT-TYPE
              SYNTAX  DisplayString (SIZE (0..255))
              ACCESS  read-write
              STATUS  mandatory
              DESCRIPTION
    	    	    "Used by Collector with its SNMP requests
                     to the MMA."
              ::= { collectInfo 3 }

         rmonCommunityName OBJECT-TYPE
              SYNTAX  DisplayString (SIZE (0..255))
              ACCESS  read-write
              STATUS  mandatory
              DESCRIPTION
    	    	    "Used by RMON/Collector with its SNMP requests
                     to the MMA."
              ::= { collectInfo 4 }



--
--
-- Edge card specific protocols
--

         lsPortProtocols        OBJECT IDENTIFIER ::= { atmSwitch 8 }

-- This table contains information specific to edge ports.
-- An object-identifier in the port table points to the
-- appropriate table for the port.

    	 edgePort	OBJECT IDENTIFIER ::= { lsPortProtocols 1 }

         edgePortTable OBJECT-TYPE
    	    SYNTAX  SEQUENCE OF EdgePortEntry
            ACCESS  not-accessible
	    STATUS  mandatory
	    DESCRIPTION
                "EdgePort Port Address table specific information"
	    ::= { edgePort 1 }

	 edgePortEntry OBJECT-TYPE
	    SYNTAX   EdgePortEntry
	    ACCESS   not-accessible
	    STATUS   mandatory
	    DESCRIPTION
	        "An entry in the EdgePort Port Address table."
	    INDEX   { edgeIfIndex }
	    ::= { edgePortTable 1 }

	 EdgePortEntry ::=
	    SEQUENCE {
	        edgeIfIndex
	        	INTEGER,
		edgeUpcType 
			INTEGER,
     	    	edgeUserDataPerCell
                        INTEGER,
		edgeCellDelayVariance
			INTEGER,
		edgePrincipalScale
			INTEGER,
		edgeSecondaryScale
    	        	INTEGER,
    	        edgeMeteringFactor
    	        	INTEGER,
    	        edgeMeteringBurstSize
    	        	INTEGER,
                edgeCallSetupRetry
    	                INTEGER,
               edgeCallSetupBackoff
                        INTEGER,
               edgeMaxFrameSize
    	    	    	INTEGER
	        }
    	        	    
        edgeIfIndex OBJECT-TYPE
              SYNTAX  INTEGER
    	      ACCESS  read-only
              STATUS  mandatory
              DESCRIPTION
                  "This is the ifIndex value of the corresponding
		  ifEntry.  See comments above."
              ::= { edgePortEntry 1 }

         edgeUpcType OBJECT-TYPE
              SYNTAX  INTEGER {
    	    	    ansiCompliant (1)
		    }
    	      ACCESS  read-write
              STATUS  mandatory
              DESCRIPTION
                  "Usage Parameter Control model type.  This parameter
		   selects the UPC model, which regulates the flow
		   of data into the network."
	      DEFVAL { 1 } -- default to the ANSI UPC model
              ::= { edgePortEntry 2 }

         edgeUserDataPerCell OBJECT-TYPE
              SYNTAX  INTEGER ( 1..384 )
    	      ACCESS  read-write
              STATUS  mandatory
              DESCRIPTION
                  "User data bits per cell.  This specifies the expected
		   packing efficiency  when frames are converted to cells.
		   It does not affect the actual packing of data into cells
		   but serves as an estimate on which bandwidth allocation
		   and other connection related functions will be based."
	      DEFVAL { 341 } -- default to 341 bits per cell average efficiency
              ::= { edgePortEntry 3 }

         edgeCellDelayVariance OBJECT-TYPE
              SYNTAX  INTEGER 
    	      ACCESS  read-write
              STATUS  mandatory
              DESCRIPTION
                  "Cell Delay Variance in microseconds.  This is the typical
		   variance in the delay added as a cell is processed by
		   an switch"
              ::= { edgePortEntry 4 }

         edgePrincipalScale OBJECT-TYPE
              SYNTAX  INTEGER
    	      ACCESS  read-write
              STATUS  mandatory
              DESCRIPTION
                  " Principal bandwidth scaling factor.  This is used to scale
		    down the actual amount of bandwidth to allocate for the 
		    principal portion of a VC's bandwidth.   This is specified
		    as a codepoint as follows:

                    Codepoints      Meaning         Comment           
		    - ----------    -------         -------           
		                                                      
		    0 - 100         x / 100         e.g., 1 => .01    
		    101 - 109       x - 100 / 1000  e.g., 101 => .001"

	      DEFVAL { 100 } -- specify a 1-1 scaling, i.e. 100%
              ::= { edgePortEntry 5 }

         edgeSecondaryScale OBJECT-TYPE
              SYNTAX  INTEGER
    	      ACCESS  read-write
              STATUS  mandatory
              DESCRIPTION
                  " Secondary bandwidth scaling factor.  This is used to scale
		    down the actual amount of bandwidth to allocate for the 
		    Secondary portion of a VC's bandwidth.   This is specified
		    as a codepoint as follows:

                    Codepoints      Meaning         Comment           
		    - ----------    -------         -------           
		                                                      
		    0 - 100         x / 100         e.g., 1 => .01    
		    101 - 109       x - 100 / 1000  e.g., 101 => .001"

	      DEFVAL { 2 } -- default to a 1-50 mapping
              ::= { edgePortEntry 6 }

         edgeMeteringFactor OBJECT-TYPE
              SYNTAX  INTEGER
    	      ACCESS  read-write
              STATUS  mandatory
              DESCRIPTION
                 "Scale factor for the metering time charge, a value (divided by 256)
		  by which to increase the time or slow down metering of traffic 
		  into the network.  A value of 256 would typically keep the metering
		  rate close to the minimum allowable rate for the aggregate 
		  information rate for the group of circuits being metered."
	      DEFVAL { 64 } -- default to metering in at 4 times the aggregate rate
              ::= { edgePortEntry 7 }

         edgeMeteringBurstSize OBJECT-TYPE
              SYNTAX  INTEGER
    	      ACCESS  read-write
              STATUS  mandatory
              DESCRIPTION
                  "This is the minimum number of cells to burst at a time"
    	      DEFVAL { 5 }
              ::= { edgePortEntry 8 }



         edgeCallSetupRetry OBJECT-TYPE
              SYNTAX   INTEGER ( 1..3600 )
              ACCESS   read-write
              STATUS   mandatory
              DESCRIPTION
                 "This specifies the initial time to wait between successive
               failed attempts to establish a connection.  This interval
               is in seconds.  An incremental backoff algorithm may applied
               to this value.  See Parameter edgeCallSetupBackoff."
    	       DEFVAL { 5 }
             ::= { edgePortEntry 9 }

         edgeCallSetupBackoff OBJECT-TYPE
              SYNTAX   INTEGER ( 1..10 )
              ACCESS   read-write
              STATUS   mandatory
              DESCRIPTION
                 "This specifies the maximum power of 2 to backoff in call
               setup retry attempts.  For each retry up to this maxumim
               the retry timer will be adjusted by multipliing by 2**(n).
               The first retry will be multiplied by 2**0 or 1, the second
               by 2**1 or 2, and so on.  The variable can range from 1 to
               10."
    	      DEFVAL { 5 }
                  ::= { edgePortEntry 10 }


         edgeMaxFrameSize OBJECT-TYPE
              SYNTAX   INTEGER ( 48..8152 )
              ACCESS   read-write
              STATUS   mandatory
              DESCRIPTION
                 "This specifies the maximum frame size that can be transmitted
		 on this edge port.  The size is specified in bytes. "
    	      DEFVAL { 1516 }
             ::= { edgePortEntry 11 }


--
--
-- Frame relay protocol
--

	frDceInfo      OBJECT IDENTIFIER ::= { lsPortProtocols 2 }

     --  Data Link Connection Management Interface

     --      The variables that configure the DLC Provider
     --		Management Interface.

     frProvMiTable OBJECT-TYPE
         SYNTAX   SEQUENCE OF FrProvMiEntry
         ACCESS   not-accessible
         STATUS   mandatory
         DESCRIPTION
            "The Parameters for the Data Link Connection Management
            Interface for the frame relay service on this
            interface."
         REFERENCE
            "Draft American National Standard T1.617-1991, Annex D"
         ::= { frDceInfo 1 }

         frProvMiEntry OBJECT-TYPE
             SYNTAX   FrProvMiEntry
             ACCESS   not-accessible
             STATUS   mandatory
             DESCRIPTION
                "The Parameters for a particular Data Link Con-
                nection Management Interface."
            INDEX { frProvMiIfIndex }
            ::= { frProvMiTable 1 }

         FrProvMiEntry ::=
             SEQUENCE {
                 frProvMiIfIndex
                     INTEGER,
                 frProvMiState
                     INTEGER,
                 frProvMiAddressLen
                     INTEGER,
-- The first group of intervals and counts is the network side
                 frProvMiNetRequestInterval
                     INTEGER,
                 frProvMiNetErrorThreshold
                     INTEGER,
                 frProvMiNetMonitoredEvents
                     INTEGER,

-- This second group of intervals and counts is the user side of an NNI
                 frProvMiUserPollingInterval
                     INTEGER,
                 frProvMiUserFullEnquiryInterval
                     INTEGER,
                 frProvMiUserErrorThreshold
                     INTEGER,
                 frProvMiUserMonitoredEvents
                     INTEGER,

                 frProvMiMaxSupportedVCs
                     INTEGER,
                 frProvMiMulticast
		     INTEGER,
		 frProvMiNetInterfaceType
		     INTEGER		 
         }

         frProvMiIfIndex OBJECT-TYPE
             SYNTAX   INTEGER
             ACCESS   read-only
             STATUS   mandatory
             DESCRIPTION
                "This is the ifIndex value of the corresponding
		  ifEntry.  See comments above."
            ::= { frProvMiEntry 1 }


         frProvMiState OBJECT-TYPE
             SYNTAX INTEGER {
                 noLmiConfigured (1),
                 lmiFRIF         (2),  -- Frame Relay Implementors Forum
                 ansiT1-617-D    (3),  -- ANSI T1.617 Annex D
		 ccittQ-933-A	 (4)   -- CCITT Q.933 Annex A
             }
             ACCESS   read-write
             STATUS   mandatory
             DESCRIPTION
                "This variable states which Data  Link  Connec-
                tion Management scheme is active (and by impli-
                cation, what DLCI it uses) on the  Frame  Relay
                interface."
            REFERENCE
               "Draft American National Standard T1.617-1991"
           DEFVAL { 3 }
           ::= { frProvMiEntry 2 }



         frProvMiAddressLen OBJECT-TYPE
             SYNTAX  INTEGER {
                     two-octets (2)
--                     three-octets (3),    not supported
--                     four-octets (4)      not supported
             }
             ACCESS  read-write
             STATUS  mandatory
             DESCRIPTION
                "This variable states which address  length  in
                octets.  In the case of Q922 format, the length
                indicates the entire length of the address  in-
                cluding the control portion."
            ::= { frProvMiEntry 3 }


-- First the Network Side config parameter 

         frProvMiNetRequestInterval OBJECT-TYPE
             SYNTAX   INTEGER (5..30)
             ACCESS   read-write
             STATUS   mandatory
             DESCRIPTION
                "This is the maximum number of seconds between
                successive status enquiry messages.  If a status
		enquiry message does not arrive within this time
		an error event occurs.  This is also refered to 
		as T392 and nT2.

		Must be 5 in second intervals as defined in the ANSI
		and ITU specifications."
            REFERENCE
               "Draft American National  Standard  T1.617-1991,
               Section D.7 Timer T392."
           DEFVAL { 15 }
           ::= { frProvMiEntry 4 }

         frProvMiNetErrorThreshold OBJECT-TYPE
             SYNTAX   INTEGER (1..10)
             ACCESS   read-write
             STATUS   mandatory
             DESCRIPTION
                "This  is  the  maximum  number  of  unanswered
                Status Enquiries the equipment shall accept be-
                fore declaring the interface down by the network
		side of the interface.  This is also refered to
		as N392 and nN2."
            REFERENCE
               "Draft American National  Standard  T1.617-1991,
               Section D.5.1 Counter N392."
           DEFVAL { 3 }
           ::= { frProvMiEntry 5 }


         frProvMiNetMonitoredEvents OBJECT-TYPE
             SYNTAX   INTEGER (1..10)
             ACCESS   read-write
             STATUS   mandatory
             DESCRIPTION
                "This is the number of status polling intervals
                over which the error threshold is counted.  For
                example, if within 'MonitoredEvents' number  of
                events  the  station  receives 'ErrorThreshold'
                number of errors, the interface  is  marked  as
                down.  This is also refered to as N393 and nN3."
            REFERENCE
               "Draft American National  Standard  T1.617-1991,
               Section D.5.2 Counter N393."
           DEFVAL { 4 }
           ::= { frProvMiEntry 6 }


         frProvMiMaxSupportedVCs OBJECT-TYPE
             SYNTAX   INTEGER
             ACCESS   read-write
             STATUS   mandatory
             DESCRIPTION
                "The maximum number of Virtual Circuits allowed
                for  this  interface.   Usually dictated by the
                Frame Relay network.  This variable will limit
		the creation of more than this number of VCs.  It
		will not delete VCs which have already been 
		configured at the time this parameter is set.

                In response to a SET, if a value less than zero
                or  higher  than the agent's maximal capability
                is configured, the agent  should  respond  bad-
                Value"
            ::= { frProvMiEntry 7 }


         frProvMiMulticast OBJECT-TYPE
             SYNTAX   INTEGER {
                         nonBroadcast (1)
--                       broadcast (2)     not supported
                         }
             ACCESS   read-write
             STATUS   mandatory
             DESCRIPTION
                "This indicates whether the Frame Relay  inter-
                face is using a multicast service."
            ::= { frProvMiEntry 8 }

-- Now parameters for the user side of a NNI

         frProvMiUserPollingInterval OBJECT-TYPE
             SYNTAX   INTEGER (5..30)
             ACCESS   read-write
             STATUS   mandatory
             DESCRIPTION
                "This is the number of seconds between  succes-
                sive status enquiry messages sent by the user
		portion of a NNI interface.  This is also 
		refered to as T391 and nT1."
            REFERENCE
               "Draft American National  Standard  T1.617-1991,
               Section D.7 Timer T391."
           DEFVAL { 10 }
           ::= { frProvMiEntry 9 }


         frProvMiUserFullEnquiryInterval OBJECT-TYPE
             SYNTAX   INTEGER (1..255)
             ACCESS   read-write
             STATUS   mandatory
             DESCRIPTION
                "Number of status enquiry intervals  that  pass
                before  issuance  of a full status enquiry mes-
                sage by the user portion of a NNI interface.
		This is also refered to as N391 and nN1."
            REFERENCE
               "Draft American National  Standard  T1.617-1991,
               Section D.7 Counter N391."
           DEFVAL { 6 }
           ::= { frProvMiEntry 10 }


         frProvMiUserErrorThreshold OBJECT-TYPE
             SYNTAX   INTEGER (1..10)
             ACCESS   read-write
             STATUS   mandatory
             DESCRIPTION
                "This  is  the  maximum  number  of  unanswered
                Status Enquiries the equipment shall accept be-
                fore declaring the interface down by the user
		side of the NNI interface.  This is also refered
		to as N392 and nT2."
            REFERENCE
               "Draft American National  Standard  T1.617-1991,
               Section D.5.1 Counter N392."
           DEFVAL { 3 }
           ::= { frProvMiEntry 11 }


         frProvMiUserMonitoredEvents OBJECT-TYPE
             SYNTAX   INTEGER (1..10)
             ACCESS   read-write
             STATUS   mandatory
             DESCRIPTION
                "This is the number of status polling intervals
                over which the error threshold is counted on a
		NNI interface.  For example, if within 
		'MonitoredEvents' number of events the station
		receives 'ErrorThreshold' number of errors, the
		interface  is  marked  as down."
            REFERENCE
               "Draft American National  Standard  T1.617-1991,
               Section D.5.2 Counter N393."
           DEFVAL { 4 }
           ::= { frProvMiEntry 12 }


         frProvMiNetInterfaceType OBJECT-TYPE
             SYNTAX INTEGER {
                 niUNI (1),
                 niNNI (2)
             }
             ACCESS   read-write
             STATUS   mandatory
             DESCRIPTION
                "This variable states which type of Network
		Interface should be used.  UNI provides for
		a User Network Interface, while NNI provides
		for a Network to Network Interface."
            REFERENCE
               "Draft American National Standard T1.617-1991"
           ::= { frProvMiEntry 13 }


--
--
-- Frame Relay Per circuit data
--

    	frCktInfo      OBJECT IDENTIFIER ::= { lsPortProtocols 3 }

     -- A Frame Relay service is a multiplexing service.  Data
     -- Link Connection Identifiers enumerate virtual circuits
     -- (permanent or dynamic) which are layered onto the underlying
     -- circuit, represented by ifEntry.  Therefore, each of the entries
     -- in the Standard MIB's Interface Table with an IfType of
     -- Frame Relay represents a Q.922 interface.  Zero or more
     -- virtual circuits are layered onto this interface and provide
     -- interconnection with various remote destinations.
     -- Each such virtual circuit is represented by an entry in the
     -- circuit table.

     --   Frame Relay Circuit Configuration Table

     -- The table describing the use of the DLCIs attached to
     -- each Frame Relay Interface.


frCktCfgTable OBJECT-TYPE
	SYNTAX	SEQUENCE OF FrCktEntry
	ACCESS	not-accessible
	STATUS	mandatory
	DESCRIPTION
		"A table containing information about specific DLCIs and
                corresponding circuits."
	::= { frCktInfo 1 }

frCktEntry OBJECT-TYPE
 	SYNTAX	FrCktEntry
 	ACCESS	not-accessible
 	STATUS	mandatory
 	DESCRIPTION
		"The information regarding a single Data Link
		Connection Identifier."
	INDEX { frCktSrcIfIndex, frCktSrcDlci }
	::= { frCktCfgTable 1 }

FrCktEntry ::=
	SEQUENCE {
		frCktSrcNode
			INTEGER,
		frCktSrcIfIndex
			INTEGER,
 		frCktSrcDlci
			LightStreamDLCI,
		frCktAdminDestNode
			INTEGER,
		frCktOperDestNode
			INTEGER,
		frCktAdminDestIfIndex
			INTEGER,
		frCktOperDestIfIndex
			INTEGER,
		frCktAdminDestDlci
			LightStreamDLCI,
		frCktOperDestDlci
			LightStreamDLCI,
		frCktAdminSrcInsuredRate
			INTEGER,
		frCktOperSrcInsuredRate
			INTEGER,
		frCktAdminSrcInsuredBurst
			INTEGER,
		frCktOperSrcInsuredBurst
			INTEGER,
		frCktAdminSrcMaxRate
			INTEGER,
		frCktOperSrcMaxRate
			INTEGER,
		frCktAdminSrcMaxBurst
			INTEGER,
		frCktOperSrcMaxBurst
			INTEGER,
		frCktAdminDestInsuredRate
			INTEGER,
		frCktOperDestInsuredRate
			INTEGER,
		frCktAdminDestInsuredBurst
			INTEGER,
		frCktOperDestInsuredBurst
			INTEGER,
		frCktAdminDestMaxRate
			INTEGER,
		frCktOperDestMaxRate
			INTEGER,
		frCktAdminDestMaxBurst
			INTEGER,
		frCktOperDestMaxBurst
			INTEGER,
		frCktAdminSecondaryScale
			INTEGER,
		frCktOperSecondaryScale
			INTEGER,
		frCktAdminPrinBwType
			INTEGER,
		frCktOperPrinBwType
			INTEGER,
		frCktAdminTransPri
			INTEGER,
		frCktOperTransPri
			INTEGER,
     	    	frCktAdminUserDataPerCell
                        INTEGER,
     	    	frCktOperUserDataPerCell
                        INTEGER,
		frCktStatus
			INTEGER
	}
 

         frCktSrcNode OBJECT-TYPE
             SYNTAX   INTEGER
             ACCESS   read-only
             STATUS   mandatory
             DESCRIPTION
                "The Node Identifier for the source
		end of this virtual circuit."
            ::= { frCktEntry 1 }

         frCktSrcIfIndex OBJECT-TYPE
             SYNTAX   INTEGER
             ACCESS   read-only
             STATUS   mandatory
             DESCRIPTION
                "The ifIndex Value of the ifEntry this  virtual
                circuit is layered onto.  See comments above to
		calculate ifIndex value."
            ::= { frCktEntry 2 }


         frCktSrcDlci OBJECT-TYPE
             SYNTAX   LightStreamDLCI
             ACCESS   read-only
             STATUS   mandatory
             DESCRIPTION
                "The Data Link Connection Identifier  for  this
                virtual circuit."
            REFERENCE
               "Draft American National  Standard  T1.618-1991,
               Section 3.3.6"
           ::= { frCktEntry 3 }

         frCktAdminDestNode OBJECT-TYPE
             SYNTAX   INTEGER
             ACCESS   read-write
             STATUS   mandatory
             DESCRIPTION
                "The Node Identifier for the Destination
		end of this virtual circuit.
		This variable takes effect when frCktStatus is set."
            ::= { frCktEntry 10 }

         frCktOperDestNode OBJECT-TYPE
             SYNTAX   INTEGER
             ACCESS   read-only
             STATUS   mandatory
             DESCRIPTION
                "The Node Identifier for the Destination
		end of this virtual circuit."
            ::= { frCktEntry 11 }

         frCktAdminDestIfIndex OBJECT-TYPE
             SYNTAX   INTEGER
             ACCESS   read-write
             STATUS   mandatory
             DESCRIPTION
                "The ifIndex Value of the ifEntry this virtual
                circuit is layered onto.  See comments above to
		calculate ifIndex.
		
		This variable takes effect when frCktStatus is set."
            ::= { frCktEntry 12 }


         frCktOperDestIfIndex OBJECT-TYPE
             SYNTAX   INTEGER
             ACCESS   read-only
             STATUS   mandatory
             DESCRIPTION
                "The ifIndex Value of the ifEntry this virtual
                circuit is layered onto.  See comments above to
		calculate ifIndex."
            ::= { frCktEntry 13 }


         frCktAdminDestDlci OBJECT-TYPE
             SYNTAX   LightStreamDLCI
             ACCESS   read-write
             STATUS   mandatory
             DESCRIPTION
                "The Data Link Connection Identifier  for  this
                virtual circuit.
		This variable takes effect when frCktStatus is set."
            REFERENCE
               "Draft American National  Standard  T1.618-1991,
               Section 3.3.6"
           ::= { frCktEntry 14 }

         frCktOperDestDlci OBJECT-TYPE
             SYNTAX   LightStreamDLCI
             ACCESS   read-only
             STATUS   mandatory
             DESCRIPTION
                "The Data Link Connection Identifier  for  this
                virtual circuit."
            REFERENCE
               "Draft American National  Standard  T1.618-1991,
               Section 3.3.6"
           ::= { frCktEntry 15 }


         frCktAdminSrcInsuredRate OBJECT-TYPE
             SYNTAX   INTEGER
             ACCESS   read-write
             STATUS   mandatory
             DESCRIPTION
                "This variable, the Insured Rate is the
		rate of insured data that the network commits
		to supporting under normal network conditions
		from Source to Destination.
		It is specified in bits per second.
		This variable takes effect when frCktStatus is set."
            REFERENCE
               "Draft American National  Standard  T1.617-1991,
               Section 6.5.19 Throughput parameter"
           DEFVAL   { 0 }  -- the default indicates no commitment
           ::= { frCktEntry 25 }

         frCktOperSrcInsuredRate OBJECT-TYPE
             SYNTAX   INTEGER
             ACCESS   read-only
             STATUS   mandatory
             DESCRIPTION
                "This variable, the Insured Rate is the 
		rate of insured data that the network commits
		to supporting under normal network conditions
		from source to destination.
		It is specified in bits per second."
            REFERENCE
               "Draft American National  Standard  T1.617-1991,
               Section 6.5.19 Throughput parameter"
           DEFVAL   { 0 }  -- the default indicates no commitment
           ::= { frCktEntry 26 }

         frCktAdminSrcInsuredBurst OBJECT-TYPE
             SYNTAX   INTEGER
             ACCESS   read-write
             STATUS   mandatory
             DESCRIPTION
                "This variable indicates the Insured Burst 
		Size, which is the amount of insured data,
                in  bytes,  that  the  network  agrees to
                transfer under normal  conditions,  during  the
                measurement interval from source to destination.
		This variable takes effect when frCktStatus is set."
            REFERENCE
               "Draft American National  Standard  T1.617-1991,
               Section 6.5.19"
           DEFVAL   { 0 }  -- the default indicates no commitment
           ::= { frCktEntry 27 }



         frCktOperSrcInsuredBurst OBJECT-TYPE
             SYNTAX   INTEGER
             ACCESS   read-only
             STATUS   mandatory
             DESCRIPTION
                "This variable indicates the Insured Burst 
		Size, which is the amount of insured data,
                in  bytes,  that  the  network agrees to
                transfer under normal  conditions,  during  the
                measurement interval from source to destination."
            REFERENCE
               "Draft American National  Standard  T1.617-1991,
               Section 6.5.19"
           DEFVAL   { 0 }  -- the default indicates no commitment
           ::= { frCktEntry 28 }


         frCktAdminSrcMaxRate OBJECT-TYPE
             SYNTAX   INTEGER
             ACCESS   read-write
             STATUS   mandatory
             DESCRIPTION
                "This variable, the Maximum Rate is the 
		the maximum amount of insured plus uninsured
		data throughput that the network agrees
		to support from source to destination.
		It is specified in bits per second.
		This variable takes effect when frCktStatus is set."
            REFERENCE
               "Draft American National  Standard  T1.617-1991,
               Section 6.5.19 Throughput parameter"
           DEFVAL   { 0 }  -- the default indicates no commitment
           ::= { frCktEntry 29 }

         frCktOperSrcMaxRate OBJECT-TYPE
             SYNTAX   INTEGER
             ACCESS   read-only
             STATUS   mandatory
             DESCRIPTION
                "This variable, the Maximum Rate is the 
		the maximum amount of insured plus uninsured
		data throughput that the network agrees
		to support from source to destination.
		It is specified in bits per second."
            REFERENCE
               "Draft American National  Standard  T1.617-1991,
               Section 6.5.19 Throughput parameter"
           DEFVAL   { 0 }  -- the default indicates no commitment
           ::= { frCktEntry 30 }

         frCktAdminSrcMaxBurst OBJECT-TYPE
             SYNTAX   INTEGER
             ACCESS   read-write
             STATUS   mandatory
             DESCRIPTION
                "This variable indicates the Total Burst Size,
		which is the maximum amount of insured plus
                uninsured data bytes that the network will at-
                tempt to deliver over the measurement interval
		from the Source to the Destination.

		This variable takes effect when frCktStatus is set."
            REFERENCE
               "Draft American National  Standard  T1.617-1991,
               Section 6.5.19"
           DEFVAL   { 0 }  -- the default indicates no commitment
                   ::= { frCktEntry 31 }

         frCktOperSrcMaxBurst OBJECT-TYPE
             SYNTAX   INTEGER
             ACCESS   read-only
             STATUS   mandatory
             DESCRIPTION
                "This variable indicates the Total Burst Size,
		which is the maximum amount of insured plus
                uninsured data bytes that the network will at-
                tempt to deliver over the measurement interval
		from the Source to the Destination."
            REFERENCE
               "Draft American National  Standard  T1.617-1991,
               Section 6.5.19"
           DEFVAL   { 0 }  -- the default indicates no commitment
                   ::= { frCktEntry 32 }


         frCktAdminDestInsuredRate OBJECT-TYPE
             SYNTAX   INTEGER
             ACCESS   not-accessible
             STATUS   mandatory
             DESCRIPTION
                "This variable, the Insured Rate is the 
		rate of insured data that the network commits
		to supporting under normal network conditions
		from destination to source.
		It is specified in bits per second.
		This variable takes effect when frCktStatus is set."
            REFERENCE
               "Draft American National  Standard  T1.617-1991,
               Section 6.5.19 Throughput parameter"
           DEFVAL   { 0 }  -- the default indicates no commitment
           ::= { frCktEntry 33 }

         frCktOperDestInsuredRate OBJECT-TYPE
             SYNTAX   INTEGER
             ACCESS   read-only
             STATUS   mandatory
             DESCRIPTION
                "This variable, the Insured Rate is the 
		rate of insured data that the network commits
		to supporting under normal network conditions
		from destination to source.
		It is specified in bits per second."
            REFERENCE
               "Draft American National  Standard  T1.617-1991,
               Section 6.5.19 Throughput parameter"
           DEFVAL   { 0 }  -- the default indicates no commitment
           ::= { frCktEntry 34 }

         frCktAdminDestInsuredBurst OBJECT-TYPE
             SYNTAX   INTEGER
             ACCESS   not-accessible
             STATUS   mandatory
             DESCRIPTION
                "This variable indicates the Insured Burst 
		Size, which is the amount  of insured 
                data,  in  bytes,  that  the  network  agrees to
                transfer under normal  conditions,  during  the
                measurement interval from destination to source.
		This variable takes effect when frCktStatus is set."
            REFERENCE
               "Draft American National  Standard  T1.617-1991,
               Section 6.5.19"
           DEFVAL   { 0 }  -- the default indicates no commitment
           ::= { frCktEntry 35 }



         frCktOperDestInsuredBurst OBJECT-TYPE
             SYNTAX   INTEGER
             ACCESS   read-only
             STATUS   mandatory
             DESCRIPTION
                "This variable indicates the Insured Burst 
		Size, which is the amount  of insured
                data,  in  bytes,  that  the  network  agrees to
                transfer under normal  conditions,  during  the
                measurement interval from destination to source."
            REFERENCE
               "Draft American National  Standard  T1.617-1991,
               Section 6.5.19"
           DEFVAL   { 0 }  -- the default indicates no commitment
           ::= { frCktEntry 36 }



         frCktAdminDestMaxRate OBJECT-TYPE
             SYNTAX   INTEGER
             ACCESS   not-accessible
             STATUS   mandatory
             DESCRIPTION
                "This variable, the Maximum Rate is the 
		the maximum amount of insured plus uninsured
		data throughput that the network agrees
		to transfer from destination to source.
		It is specified in bits per second.
		This variable takes effect when frCktStatus is set."
            REFERENCE
               "Draft American National  Standard  T1.617-1991,
               Section 6.5.19 Throughput parameter"
           DEFVAL   { 0 }  -- the default indicates no commitment
           ::= { frCktEntry 37 }

         frCktOperDestMaxRate OBJECT-TYPE
             SYNTAX   INTEGER
             ACCESS   read-only
             STATUS   mandatory
             DESCRIPTION
                "This variable, the maximum rate is the total
		data throughput that the network will allow
		to pass on this VC under optimal network conditions
		from destination to source.
		It is specified in bits per second."
            REFERENCE
               "Draft American National  Standard  T1.617-1991,
               Section 6.5.19 Throughput parameter"
           DEFVAL   { 0 }  -- the default indicates no commitment
           ::= { frCktEntry 38 }

         frCktAdminDestMaxBurst OBJECT-TYPE
             SYNTAX   INTEGER
             ACCESS   not-accessible
             STATUS   mandatory
             DESCRIPTION
                "This variable indicates the Total Burst Size,
		which is the maximum amount of insured plus
                uninsured data bytes that the network will at-
                tempt to deliver over the measurement interval
		from the Destination to the Source.
		This variable takes effect when frCktStatus is set."
            REFERENCE
               "Draft American National  Standard  T1.617-1991,
               Section 6.5.19"
           DEFVAL   { 0 }  -- the default indicates no commitment
                   ::= { frCktEntry 39 }
 

         frCktOperDestMaxBurst OBJECT-TYPE
             SYNTAX   INTEGER
             ACCESS   read-only
             STATUS   mandatory
             DESCRIPTION
                "This variable indicates the Total Burst Size,
		which is the maximum amount of insured plus
                uninsured data bytes that the network will at-
                tempt to deliver over the measurement interval
		from the Destination to the Source."

            REFERENCE
               "Draft American National  Standard  T1.617-1991,
               Section 6.5.19"
           DEFVAL   { 0 }  -- the default indicates no commitment
                   ::= { frCktEntry 40 }


	frCktOperSecondaryScale OBJECT-TYPE
          SYNTAX  INTEGER
	  ACCESS  read-only
          STATUS  mandatory
          DESCRIPTION
            "Operational version of the Secondary bandwidth scaling 
	     factor.  This is used to scale down the actual amount of
	     bandwidth to allocate for the Secondary portion of a VC's
	     bandwidth.   This is specified as a codepoint as follows:

             Codepoints      Meaning         Comment           
	     - ----------    -------         -------           
	                                                       
	     0 - 100         x / 100         e.g., 1 => .01    
	     101 - 109       x - 100 / 1000  e.g., 101 => .001 
	     254             (reserved)      
	     255             (per-port dflt)"

           DEFVAL   { 255 }  -- the default indicates that the port 
			     -- variable should be used
           ::= { frCktEntry 41 }

	frCktAdminSecondaryScale OBJECT-TYPE
           SYNTAX  INTEGER
 	   ACCESS  read-write
           STATUS  mandatory
           DESCRIPTION
            "Secondary bandwidth scaling factor.  This is used to scale
	     down the actual amount of bandwidth to allocate for the 
	     Secondary portion of a VC's bandwidth.   This is specified
	     as a codepoint as follows:

             Codepoints      Meaning         Comment           
	     - ----------    -------         -------           
	                                                       
	     0 - 100         x / 100         e.g., 1 => .01    
	     101 - 109       x - 100 / 1000  e.g., 101 => .001 
	     254             (reserved)      
	     255             (per-port dflt)"

           DEFVAL   { 255 }  -- the default indicates that the port 
			     -- variable should be used
                   ::= { frCktEntry 42 }

         frCktOperPrinBwType OBJECT-TYPE
             SYNTAX   INTEGER {
		guaranteed (1),
		insured (2)
		}
             ACCESS   read-only
             STATUS   mandatory
             DESCRIPTION
                "This variable indicates the type of service supported
		on primary portion of this Virtual Circuit."
	    DEFVAL   { 1 }  -- use Insured by default
                    ::= { frCktEntry 43 }

         frCktAdminPrinBwType OBJECT-TYPE
             SYNTAX   INTEGER  {
		guaranteed (1),
		insured (2)
		}
             ACCESS   read-write
             STATUS   mandatory
             DESCRIPTION
                "This variable indicates the type of service supported
		on primary portion of this Virtual Circuit.
 
		This variable takes effect when frCktStatus is set."
	    DEFVAL   { 1 }  -- use Insured by default
                    ::= { frCktEntry 44 }

         frCktOperTransPri OBJECT-TYPE
             SYNTAX   INTEGER  (0..1)
             ACCESS   read-only
             STATUS   mandatory
             DESCRIPTION
                "This variable indicates the transfer priority supported
		on this Virtual Circuit."
	    DEFVAL   { 0 }  -- use priority DG0 by default
                    ::= { frCktEntry 45 }

         frCktAdminTransPri OBJECT-TYPE
             SYNTAX   INTEGER (0..1)
             ACCESS   read-write
             STATUS   mandatory
             DESCRIPTION
                "This variable indicates the transfer priority supported
		on this Virtual Circuit.
 
		This variable takes effect when frCktStatus is set."
	    DEFVAL   { 0 }  -- use priority DG0 by default
                    ::= { frCktEntry 46 }

         frCktOperUserDataPerCell OBJECT-TYPE
              SYNTAX  INTEGER ( 0..384 )
    	      ACCESS  read-only
              STATUS  mandatory
              DESCRIPTION
                  "Operational User data bits per cell, specifies the expected
		   packing efficiency when frames are converted to cells.
		   It does not affect the actual packing of data into cells
		   but serves as an estimate on which bandwidth allocation
		   and other connection related functions will be based."
	      DEFVAL   { 0 }  -- the default indicates that the port 
			     -- variable should be used
              ::= { frCktEntry 47 }

         frCktAdminUserDataPerCell OBJECT-TYPE
              SYNTAX  INTEGER ( 0..384 )
    	      ACCESS  read-write
              STATUS  mandatory
              DESCRIPTION
                  "Administrative User data bits per cell, specifies the expected
		   packing efficiency  when frames are converted to cells.
		   It does not affect the actual packing of data into cells
		   but serves as an estimate on which bandwidth allocation
		   and other connection related functions will be based.
 
		   This variable takes effect when frCktStatus is set."
	      DEFVAL   { 0 }  -- the default indicates that the port 
			     -- variable should be used
              ::= { frCktEntry 48 }

         frCktStatus OBJECT-TYPE
             SYNTAX   INTEGER {
		enabled (1),
		disabled (2),
		delete (3)
		}
             ACCESS   read-write
             STATUS   mandatory
             DESCRIPTION
                "This variable indicates the Status of this Virtual
		Circuit.  It may be enabled or disabled.  

		In order to modify a Virtual Circuit, the new
		desired variables should be modified and then
		this variable should be set (or set again) to
		enabled.  At that time desired variables will
		become the actual variables.

		To remove a PVC, set its status to delete.
 
                By default, if not configured when creating the
                entry, the status is disabled."
 
                   ::= { frCktEntry 99 }

--
     -- Frame Relay Circuit Information Table

     -- The table describing the state of the DLCIs attached to
     -- each Frame Relay Interface.


frCktInfoTable OBJECT-TYPE
	SYNTAX	SEQUENCE OF FrCktInfoEntry
	ACCESS	not-accessible
	STATUS	mandatory
	DESCRIPTION
		"A table containing information about specific DLCIs and
                corresponding circuits."
	::= { frCktInfo 2 }

frCktInfoEntry OBJECT-TYPE
 	SYNTAX	FrCktInfoEntry
 	ACCESS	not-accessible
 	STATUS	mandatory
 	DESCRIPTION
		"The information regarding a single Data Link
		Connection Identifier."
	INDEX { frCktInfoIfIndex, frCktInfoDlci }
	::= { frCktInfoTable 1 }

FrCktInfoEntry ::=
	SEQUENCE {
		frCktInfoIfIndex
			INTEGER,
 		frCktInfoDlci
			LightStreamDLCI,
		frCktInfoLclLMI		-- LMI
			INTEGER,
		frCktInfoRmtLMI		-- LMI
			INTEGER,
		frCktInfoCallIDIncoming
			INTEGER,
		frCktInfoCallIDOutgoing
			INTEGER,
		frCktInfoDownstreamState
			INTEGER,
		frCktInfoUpstreamState
			INTEGER,
		frCktInfoLastAtmErr
			OCTET STRING,
		frCktInfoLastAtmLocation
			DisplayString (SIZE (0..30)),
	        frCktInfoDataCellsRequired
			INTEGER
	}

         frCktInfoIfIndex OBJECT-TYPE
             SYNTAX   INTEGER
             ACCESS   read-only
             STATUS   mandatory
             DESCRIPTION
                "The ifIndex Value of the ifEntry this  virtual
                circuit is layered onto.  See comments above to
		calculate ifIndex."
                   ::= { frCktInfoEntry 1 }



         frCktInfoDlci OBJECT-TYPE
             SYNTAX   LightStreamDLCI
             ACCESS   read-only
             STATUS   mandatory
             DESCRIPTION
                "The Data Link Connection Identifier  for  this
                virtual circuit."
            REFERENCE
               "Draft American National  Standard  T1.618-1991,
               Section 3.3.6"
                   ::= { frCktInfoEntry 2 }

         frCktInfoLclLMI OBJECT-TYPE
             SYNTAX   INTEGER {
		active(1),
		inactive(2)
	     }
             ACCESS   read-only
             STATUS   mandatory
             DESCRIPTION
                "This variable indicates the local LMI
		state of the circuit."
                   ::= { frCktInfoEntry 3 }

         frCktInfoRmtLMI OBJECT-TYPE
             SYNTAX   INTEGER {
		active(1),
		inactive(2)
	     }
             ACCESS   read-only
             STATUS   mandatory
             DESCRIPTION
                "This variable indicates the remote LMI
		state of the circuit."
                   ::= { frCktInfoEntry 4 }


	--  This call id can be used to access the call progress table and the
	--  line card statistics table.

         frCktInfoCallIDIncoming OBJECT-TYPE
             SYNTAX   INTEGER
             ACCESS   read-only
             STATUS   mandatory
             DESCRIPTION
                "This variable indicates the Call Identifier
		assigned to the incomming half of this circuit."
                   ::= { frCktInfoEntry 5 }

         frCktInfoCallIDOutgoing OBJECT-TYPE
             SYNTAX   INTEGER
             ACCESS   read-only
             STATUS   mandatory
             DESCRIPTION
                "This variable indicates the Call Identifier
		assigned to the outgoing half of this circuit."
                   ::= { frCktInfoEntry 6 }

         frCktInfoDownstreamState OBJECT-TYPE
             SYNTAX   INTEGER {
		active(1),
		inactive(2)
	     }
             ACCESS   read-only
             STATUS   mandatory
             DESCRIPTION
                "This variable indicates the state of the downstream
		half of the circuit.  (passing data from the local port
		to the remote end of the network)"
                   ::= { frCktInfoEntry 7 }

         frCktInfoUpstreamState OBJECT-TYPE
             SYNTAX   INTEGER {
		active(1),
		inactive(2)
	     }
             ACCESS   read-only
             STATUS   mandatory
             DESCRIPTION
                "This variable indicates the state of the upstream
		half of the circuit.  (passing data from the port
		at the remote end of the network to the local port)"
                   ::= { frCktInfoEntry 8 }


         frCktInfoLastAtmErr OBJECT-TYPE
             SYNTAX   OCTET STRING 
             ACCESS   read-only
             STATUS   mandatory
             DESCRIPTION
                "This variable indicates the last error, if any,
		returned by the Atm Connection Management layer
		when an attempt was made to create a connection 
		or flow."
                   ::= { frCktInfoEntry 9 }

         frCktInfoDataCellsRequired OBJECT-TYPE
             SYNTAX   INTEGER
             ACCESS   read-only
             STATUS   mandatory
             DESCRIPTION
                "This variable indicates the bandwidth in
		 cells needed to establish this VC.  The
		 value returned combines the committed and
		 the Secondary bandwidth needs."
                   ::= { frCktInfoEntry 10 }

         frCktInfoLastAtmLocation OBJECT-TYPE
             SYNTAX   DisplayString (SIZE (0..30))
             ACCESS   read-only
             STATUS   mandatory
             DESCRIPTION
                "This variable indicates the last error, if any,
		returned by the Atm Connection Management layer
		when an attempt was made to create a connection 
		or flow.
		The format of the string is:
		     nodenum:ifIndex
		where all numbers are specified in decimal.  For example
		     5142:6000
		refers to the remote endpoint with node 5142, ifIndex 6000 
		(slot 6 port 0 fr type 0)."
                   ::= { frCktInfoEntry 11  }

--
--
-- Frame Forwarding Protocol Data
--

	ffCktInfo      OBJECT IDENTIFIER ::= { lsPortProtocols 4 }

     -- A Frame Forwarding service is a level 2 transport service providing
     -- a virtual circuit across and Network.

     -- Frame Forwarding Circuit Configuration Table

     -- The table describes the use of the VCs attached to
     -- each Frame Forwarding Interface.

ffCktCfgTable OBJECT-TYPE
	SYNTAX	SEQUENCE OF FfCktEntry
	ACCESS	not-accessible
	STATUS	mandatory
	DESCRIPTION
		"A table containing information about Frame Forwarding
                circuits for every port."
	::= { ffCktInfo 1 }

ffCktEntry OBJECT-TYPE
 	SYNTAX	FfCktEntry
 	ACCESS	not-accessible
 	STATUS	mandatory
 	DESCRIPTION
		"The information regarding a single Data Link
		Connection Identifier."
	INDEX { ffCktSrcIfIndex }
	::= { ffCktCfgTable 1 }

FfCktEntry ::=
	SEQUENCE {
		ffCktSrcNode
			INTEGER,
		ffCktSrcIfIndex
			INTEGER,
		ffCktAdminDestNode
			INTEGER,
		ffCktOperDestNode
			INTEGER,
		ffCktAdminDestIfIndex
			INTEGER,
		ffCktOperDestIfIndex
			INTEGER,
		ffCktAdminSrcInsuredRate
			INTEGER,
		ffCktOperSrcInsuredRate
			INTEGER,
		ffCktAdminSrcInsuredBurst
			INTEGER,
		ffCktOperSrcInsuredBurst
			INTEGER,
		ffCktAdminSrcMaxRate
			INTEGER,
		ffCktOperSrcMaxRate
			INTEGER,
		ffCktAdminSrcMaxBurst
			INTEGER,
		ffCktOperSrcMaxBurst
			INTEGER,
		ffCktAdminDestInsuredRate
			INTEGER,
		ffCktOperDestInsuredRate
			INTEGER,
		ffCktAdminDestInsuredBurst
			INTEGER,
		ffCktOperDestInsuredBurst
			INTEGER,
		ffCktAdminDestMaxRate
			INTEGER,
		ffCktOperDestMaxRate
			INTEGER,
		ffCktAdminDestMaxBurst
			INTEGER,
		ffCktOperDestMaxBurst
			INTEGER,
		ffCktAdminPrinBwType
			INTEGER,
		ffCktOperPrinBwType
			INTEGER,
		ffCktAdminTransPri
			INTEGER,
		ffCktOperTransPri
			INTEGER,
		ffCktStatus
			INTEGER
	}
 

         ffCktSrcNode OBJECT-TYPE
             SYNTAX   INTEGER
             ACCESS   read-only
             STATUS   mandatory
             DESCRIPTION
                "The Node Identifier for the source
		end of this virtual circuit."
            ::= { ffCktEntry 1 }

         ffCktSrcIfIndex OBJECT-TYPE
             SYNTAX   INTEGER
             ACCESS   read-only
             STATUS   mandatory
             DESCRIPTION

                "The ifIndex Value of the ifEntry this  virtual
                circuit is layered onto.  See above comments to
		calculate ifIndex."
            ::= { ffCktEntry 2 }

         ffCktAdminDestNode OBJECT-TYPE
             SYNTAX   INTEGER
             ACCESS   read-write
             STATUS   mandatory
             DESCRIPTION
                "The Node Identifier for the Destination
		end of this virtual circuit.
		This variable takes effect when ffCktStatus is set."
            ::= { ffCktEntry 9 }

         ffCktOperDestNode OBJECT-TYPE
             SYNTAX   INTEGER
             ACCESS   read-only
             STATUS   mandatory
             DESCRIPTION
                "The Node Identifier for the Destination
		end of this virtual circuit."
            ::= { ffCktEntry 10 }

         ffCktAdminDestIfIndex OBJECT-TYPE
             SYNTAX   INTEGER
             ACCESS   read-write
             STATUS   mandatory
             DESCRIPTION
                "The ifIndex Value of the ifEntry this virtual
                circuit is layered onto.  See above comments to
		calculate ifIndex.
		
		This variable takes effect when ffCktStatus is set."
            ::= { ffCktEntry 11 }

         ffCktOperDestIfIndex OBJECT-TYPE
             SYNTAX   INTEGER
             ACCESS   read-only
             STATUS   mandatory
             DESCRIPTION
                "The ifIndex Value of the ifEntry this virtual
                circuit is layered onto.  See above comments to
		calculate ifIndex."
            ::= { ffCktEntry 12 }


         ffCktAdminSrcInsuredRate OBJECT-TYPE
             SYNTAX   INTEGER
             ACCESS   read-write
             STATUS   mandatory
             DESCRIPTION
                "This variable, the Insured Rate is the 
		rate of insured data that the network commits
		to supporting under normal network conditions
		from source to destination.
		This is specified in bits per second.
		This variable takes effect when ffCktStatus is set."
           DEFVAL   { 0 }  -- the default indicates no commitment
           ::= { ffCktEntry 21 }

         ffCktOperSrcInsuredRate OBJECT-TYPE
             SYNTAX   INTEGER
             ACCESS   read-only
             STATUS   mandatory
             DESCRIPTION
                "This variable, the Insured Rate is the 
		rate of insured data that the network commits
		to supporting under normal network conditions
		from source to destination.
		This is specified in bits per second."
             DEFVAL   { -11 }  -- the default permits system to choose a value
           ::= { ffCktEntry 22 }

         ffCktAdminSrcInsuredBurst OBJECT-TYPE
             SYNTAX   INTEGER
             ACCESS   read-write
             STATUS   mandatory
             DESCRIPTION
                "This variable indicates the Insured Burst 
		Size, which is the amount of insured
                data,  in  bytes,  that  the  network  agrees to
                transfer under normal  conditions,  during  the
                measurement interval from source to destination.
		This variable takes effect when ffCktStatus is set."
             DEFVAL   { -1 }  -- the default permits system to choose a value
           ::= { ffCktEntry 23 }
 

         ffCktOperSrcInsuredBurst OBJECT-TYPE
             SYNTAX   INTEGER
             ACCESS   read-only
             STATUS   mandatory
             DESCRIPTION
                "This variable indicates the Insured Burst 
		Size, which is the amount of insured
                data,  in  bytes,  that  the  network  agrees to
                transfer under normal  conditions,  during  the
                measurement interval from source to destination."
             DEFVAL   { -1 }  -- the default permits system to choose a value
           ::= { ffCktEntry 24 }

         ffCktAdminSrcMaxRate OBJECT-TYPE
             SYNTAX   INTEGER
             ACCESS   read-write
             STATUS   mandatory
             DESCRIPTION
                "This variable, the Maximum Rate is the 
		the maximum amount of insured plus uninsured
		data throughput that the network agrees
		to transfer from source to destination.
		This is specified in bits per second.
		This variable takes effect when ffCktStatus is set."
             DEFVAL   { -1 }  -- the default permits system to choose a value
           ::= { ffCktEntry 25 }

         ffCktOperSrcMaxRate OBJECT-TYPE
             SYNTAX   INTEGER
             ACCESS   read-only
             STATUS   mandatory
             DESCRIPTION
                "This variable, the Maximum Rate is the 
		the maximum amount of insured plus uninsured
		data throughput that the network agrees
		to support from source to destination.
		This is specified in bits per second."
             DEFVAL   { -1 }  -- the default permits system to choose a value
           ::= { ffCktEntry 26 }

         ffCktAdminSrcMaxBurst OBJECT-TYPE
             SYNTAX   INTEGER
             ACCESS   read-write
             STATUS   mandatory
             DESCRIPTION
                "This variable indicates the Total Burst Size,
		the maximum amount of insured plus uninsured
                data,  in  bytes,  that  the  network  agrees to
                transfer under normal  conditions,  during  the
                measurement interval from source to destination.
		This variable takes effect when ffCktStatus is set."
             DEFVAL   { -1 }  -- the default permits system to choose a value
           ::= { ffCktEntry 27 }
 

         ffCktOperSrcMaxBurst OBJECT-TYPE
             SYNTAX   INTEGER
             ACCESS   read-only
             STATUS   mandatory
             DESCRIPTION
                "This variable indicates the Total Burst Size,
		the maximum amount of insured plus uninsured
                data,  in  bytes,  that  the  network  agrees to
                transfer under normal  conditions,  during  the
                measurement interval from source to destination."
             DEFVAL   { -1 }  -- the default permits system to choose a value
           ::= { ffCktEntry 28 }
 
         ffCktAdminDestInsuredRate OBJECT-TYPE
             SYNTAX   INTEGER
             ACCESS   not-accessible
             STATUS   mandatory
             DESCRIPTION
                "This variable, the Insured Rate is the 
		rate of insured data that the network commits
		to supporting under normal network conditions
		from destination to source.
		This is specified in bits per second.
		This variable takes effect when ffCktStatus is set."
             DEFVAL   { -1 }  -- the default permits system to choose a value
           ::= { ffCktEntry 29 }

         ffCktOperDestInsuredRate OBJECT-TYPE
             SYNTAX   INTEGER
             ACCESS   read-only
             STATUS   mandatory
             DESCRIPTION
                "This variable, the Insured Rate is the 
		rate of insured data that the network commits
		to supporting under normal network conditions
		from destination to source.
		This is specified in bits per second."
             DEFVAL   { -1 }  -- the default permits system to choose a value
           ::= { ffCktEntry 30 }

         ffCktAdminDestInsuredBurst OBJECT-TYPE
             SYNTAX   INTEGER
             ACCESS   not-accessible
             STATUS   mandatory
             DESCRIPTION
                "This variable indicates the Insured Burst 
		Size, which is the amount of insured
                data,  in  bytes,  that  the  network  agrees to
                transfer under normal  conditions,  during  the
                measurement interval from destination to source.
		This variable takes effect when ffCktStatus is set."
             DEFVAL   { -1 }  -- the default permits system to choose a value
           ::= { ffCktEntry 31 }
 

         ffCktOperDestInsuredBurst OBJECT-TYPE
             SYNTAX   INTEGER
             ACCESS   read-only
             STATUS   mandatory
             DESCRIPTION
                "This variable indicates the Insured Burst 
		Size, which is the amount  of insured
                data,  in  bytes,  that  the  network  agrees to
                transfer under normal  conditions,  during  the
                measurement interval from destination to source."
             DEFVAL   { -1 }  -- the default permits system to choose a value
           ::= { ffCktEntry 32 }


         ffCktAdminDestMaxRate OBJECT-TYPE
             SYNTAX   INTEGER
             ACCESS   not-accessible
             STATUS   mandatory
             DESCRIPTION
                "This variable, the Maximum Rate is the 
		the maximum amount of insured plus uninsured
		data throughput that the network agrees
		to transfer from destination to source.
		This is specified in bits per second.
		This variable takes effect when ffCktStatus is set."
             DEFVAL   { -1 }  -- the default permits system to choose a value
           ::= { ffCktEntry 33 }

         ffCktOperDestMaxRate OBJECT-TYPE
             SYNTAX   INTEGER
             ACCESS   read-only
             STATUS   mandatory
             DESCRIPTION
                "This variable, the Maximum Rate is the 
		the maximum amount of insured plus uninsured
		data throughput that the network agrees
		to support from destination to source.
		This is specified in bits per second."
             DEFVAL   { -1 }  -- the default permits system to choose a value
           ::= { ffCktEntry 34 }

         ffCktAdminDestMaxBurst OBJECT-TYPE
             SYNTAX   INTEGER
             ACCESS   not-accessible
             STATUS   mandatory
             DESCRIPTION
                "This variable indicates the Total Burst Size,
		the maximum amount of insured plus uninsured
                data,  in  bytes,  that  the  network  agrees to
                transfer during  the measurement interval from 
		destination to source.
		This variable takes effect when ffCktStatus is set."

             DEFVAL   { -1 }  -- the default permits system to choose a value
           ::= { ffCktEntry 35 }
 

         ffCktOperDestMaxBurst OBJECT-TYPE
             SYNTAX   INTEGER
             ACCESS   read-only
             STATUS   mandatory
             DESCRIPTION
                "This variable indicates the Total Burst Size,
		the maximum amount of insured plus uninsured
                data,  in  bytes,  that  the  network  agrees to
                transfer,  during  the measurement interval 
		from destination to source."

             DEFVAL   { -1 }  -- the default permits system to choose a value
           ::= { ffCktEntry 36 }
 

         ffCktOperPrinBwType OBJECT-TYPE
             SYNTAX   INTEGER {
		guaranteed (1),
		insured (2)
		}
             ACCESS   read-only
             STATUS   mandatory
             DESCRIPTION
                "This variable indicates the type of service supported
		on primary portion of this Virtual Circuit."
	    DEFVAL   { 1 }  -- use Guaranteed by default
                    ::= { ffCktEntry 37 }

         ffCktAdminPrinBwType OBJECT-TYPE
             SYNTAX   INTEGER  {
		guaranteed (1),
		insured (2)
		}
             ACCESS   read-write
             STATUS   mandatory
             DESCRIPTION
                "This variable indicates the type of service supported
		on primary portion of this Virtual Circuit.
 
		This variable takes effect when ffCktStatus is set."
	    DEFVAL   { 1 }  -- use Guaranteed by default
                    ::= { ffCktEntry 38 }

         ffCktOperTransPri OBJECT-TYPE
             SYNTAX   INTEGER  (0..1)
             ACCESS   read-only
             STATUS   mandatory
             DESCRIPTION
                "This variable indicates the transfer priority supported
		on this Virtual Circuit."
	    DEFVAL   { 1 }  -- use priority DG1 by default
                    ::= { ffCktEntry 39 }

         ffCktAdminTransPri OBJECT-TYPE
             SYNTAX   INTEGER (0..1)
             ACCESS   read-write
             STATUS   mandatory
             DESCRIPTION
                "This variable indicates the transfer priority supported
		on this Virtual Circuit.
 
		This variable takes effect when ffCktStatus is set."
	    DEFVAL   { 1 }  -- use priority DG1 by default
                    ::= { ffCktEntry 40 }

         ffCktStatus OBJECT-TYPE
             SYNTAX   INTEGER {
		enabled (1),
		disabled (2),
		delete (3)
		}
             ACCESS   read-write
             STATUS   mandatory
             DESCRIPTION
                "This variable indicates the Status of this Virtual
		Circuit.  It may be enabled or disabled.  

		In order to modify a Virtual Circuit, the new
		desired variables should be modified and then
		this variable should be set (or set again) to
		enabled.  At that time desired variables will
		become the actual variables.

		To remove a PVC, set its status to delete.
 
                By default, if not configured when creating the
                entry, the status is disabled."
 
                   ::= { ffCktEntry 99 }

--
     -- Frame Forwarding Circuit Information Table

     -- The table describing the state of the VC attached to
     -- each Frame Forwarding Interface.

ffCktInfoTable OBJECT-TYPE
	SYNTAX	SEQUENCE OF FfCktInfoEntry
	ACCESS	not-accessible
	STATUS	mandatory
	DESCRIPTION
		"A table containing information about specific Frame
                Forwarding virtual circuits."
	::= { ffCktInfo 2 }

ffCktInfoEntry OBJECT-TYPE
 	SYNTAX	FfCktInfoEntry
 	ACCESS	not-accessible
 	STATUS	mandatory
 	DESCRIPTION
		"The information regarding a single Data Link
		Connection Identifier."
	INDEX { ffCktInfoIfIndex }
	::= { ffCktInfoTable 1 }

FfCktInfoEntry ::=
	SEQUENCE {
		ffCktInfoIfIndex
			INTEGER,
		ffCktInfoDownstreamState
			INTEGER,
		ffCktInfoUpstreamState
			INTEGER,
		ffCktInfoCallIDIncoming
			INTEGER,
		ffCktInfoCallIDOutgoing
			INTEGER,
	        ffCktInfoLastAtmErr
             		OCTET STRING,
	        ffCktInfoLastAtmLocation
			DisplayString (SIZE (0..30)),
	        ffCktInfoDataCellsRequired
			INTEGER
	}

         ffCktInfoIfIndex OBJECT-TYPE
             SYNTAX   INTEGER
             ACCESS   read-only
             STATUS   mandatory
             DESCRIPTION
                "The ifIndex Value of the ifEntry this  virtual
                circuit is layered onto.  See above comments to
		calculate ifIndex."
                   ::= { ffCktInfoEntry 1 }

         ffCktInfoDownstreamState OBJECT-TYPE
             SYNTAX   INTEGER {
		active(1),
		inactive(2)
	     }
             ACCESS   read-only
             STATUS   mandatory
             DESCRIPTION
                "This variable indicates the state of the downstream
		half of the circuit.  (passing data from the local port
		to the remote end of the network)"
                   ::= { ffCktInfoEntry 2 }

         ffCktInfoUpstreamState OBJECT-TYPE
             SYNTAX   INTEGER {
		active(1),
		inactive(2)
	     }
             ACCESS   read-only
             STATUS   mandatory
             DESCRIPTION
                "This variable indicates the state of the upstream
		half of the circuit.  (passing data from the port
		at the remote end of the network to the local port)"
                   ::= { ffCktInfoEntry 3 }

	--  This call id can be used to access the call progress table and the
	--  line card statistics table.

         ffCktInfoCallIDIncoming OBJECT-TYPE
             SYNTAX   INTEGER
             ACCESS   read-only
             STATUS   mandatory
             DESCRIPTION
                "This variable indicates the Call Identifier
		assigned to the incomming half of this circuit."
                   ::= { ffCktInfoEntry 4 }

         ffCktInfoCallIDOutgoing OBJECT-TYPE
             SYNTAX   INTEGER
             ACCESS   read-only
             STATUS   mandatory
             DESCRIPTION
                "This variable indicates the Call Identifier
		assigned to the outgoing half of this circuit."
                   ::= { ffCktInfoEntry 5 }


         ffCktInfoLastAtmErr OBJECT-TYPE
             SYNTAX   OCTET STRING 
             ACCESS   read-only
             STATUS   mandatory
             DESCRIPTION
                "This variable indicates the last error, if any,
		returned by the Atm Connection Management layer
		when an attempt was made to create a connection 
		or flow."
                   ::= { ffCktInfoEntry 6 }

         ffCktInfoDataCellsRequired OBJECT-TYPE
             SYNTAX   INTEGER
             ACCESS   read-only
             STATUS   mandatory
             DESCRIPTION
                "This variable indicates the bandwidth in
		 cells needed to establish this VC.  The
		 value returned combines the committed and
		 the Secondary bandwidth needs."
                   ::= { ffCktInfoEntry 7 }

         ffCktInfoLastAtmLocation OBJECT-TYPE
             SYNTAX   DisplayString (SIZE (0..30))
             ACCESS   read-only
             STATUS   mandatory
             DESCRIPTION
                "This variable indicates the last error, if any,
		returned by the Atm Connection Management layer
		when an attempt was made to create a connection 
		or flow.
		The format of the string is:
		     nodenum:ifIndex
		where all numbers are specified in decimal.  For example
		     5142:6000
		refers to the remote endpoint with node 5142, ifIndex 6000 
		(slot 6 port 0 frType 0)."
                   ::= { ffCktInfoEntry 8  }

--
--
-- Simple (ATM) UNI  protocol
--

--
-- Simple (ATM) UNI Per circuit data
--

    	sUniCktInfo      OBJECT IDENTIFIER ::= { lsPortProtocols 5 }

     -- A Simple (ATM) UNI service is a multiplexing service.  Virtual 
     -- Circuit Identifiers (VCIs) enumerate virtual circuits
     -- (permanent or dynamic) which are layered onto the underlying
     -- circuit, represented by ifEntry.  Therefore, each of the entries
     -- in the Standard MIB's Interface Table with an IfType of Simple (ATM) 
     -- UNI represents this type of interface interface.  Zero or more
     -- virtual circuits are layered onto this interface and provide
     -- interconnection with various remote destinations.
     -- Each such virtual circuit is represented by an entry in the
     -- circuit table.

     --   Simple (ATM) UNI Circuit Configuration Table

     -- The table describing the use of the VCIs attached to
     -- each Simple (ATM) UNI Interface.


sUniCktCfgTable OBJECT-TYPE
	SYNTAX	SEQUENCE OF SUniCktEntry
	ACCESS	not-accessible
	STATUS	mandatory
	DESCRIPTION
		"A table containing information about specific VCIs and
                corresponding circuits."
	::= { sUniCktInfo 1 }

sUniCktEntry OBJECT-TYPE
 	SYNTAX	SUniCktEntry
 	ACCESS	not-accessible
 	STATUS	mandatory
 	DESCRIPTION
		"The information regarding a single Data Link
		Connection Identifier."
	INDEX { sUniCktSrcIfIndex, sUniCktSrcVCI }
	::= { sUniCktCfgTable 1 }

SUniCktEntry ::=
	SEQUENCE {
		sUniCktSrcNode
			INTEGER,
		sUniCktSrcIfIndex
			INTEGER,
 		sUniCktSrcVCI
			VCI,
		sUniCktAdminDestNode
			INTEGER,
		sUniCktOperDestNode
			INTEGER,
		sUniCktAdminDestIfIndex
			INTEGER,
		sUniCktOperDestIfIndex
			INTEGER,
		sUniCktAdminDestVCI
			VCI,
		sUniCktOperDestVCI
			VCI,
		sUniCktAdminPrinBwType
			INTEGER,
		sUniCktOperPrinBwType
			INTEGER,
		sUniCktAdminTransPri
			INTEGER,
		sUniCktOperTransPri
			INTEGER,
		sUniCktAdminSrcInsuredRate
			INTEGER,
		sUniCktOperSrcInsuredRate
			INTEGER,
		sUniCktAdminSrcInsuredBurst
			INTEGER,
		sUniCktOperSrcInsuredBurst
			INTEGER,
		sUniCktAdminSrcMaxRate
			INTEGER,
		sUniCktOperSrcMaxRate
			INTEGER,
		sUniCktAdminSrcMaxBurst
			INTEGER,
		sUniCktOperSrcMaxBurst
			INTEGER,
		sUniCktAdminDestInsuredRate
			INTEGER,
		sUniCktOperDestInsuredRate
			INTEGER,
		sUniCktAdminDestInsuredBurst
			INTEGER,
		sUniCktOperDestInsuredBurst
			INTEGER,
		sUniCktAdminDestMaxRate
			INTEGER,
		sUniCktOperDestMaxRate
			INTEGER,
		sUniCktAdminDestMaxBurst
			INTEGER,
		sUniCktOperDestMaxBurst
			INTEGER,
		sUniCktAdminSecondaryScale
			INTEGER,
		sUniCktOperSecondaryScale
			INTEGER,
		sUniCktSts
			INTEGER
	}
 

         sUniCktSrcNode OBJECT-TYPE
             SYNTAX   INTEGER
             ACCESS   read-only
             STATUS   mandatory
             DESCRIPTION
                "The Node Identifier for the source
		end of this virtual circuit."
            ::= { sUniCktEntry 1 }

         sUniCktSrcIfIndex OBJECT-TYPE
             SYNTAX   INTEGER
             ACCESS   read-only
             STATUS   mandatory
             DESCRIPTION
                "The ifIndex Value of the ifEntry this  virtual
                circuit is layered onto.  See above comments to
		calculate ifIndex."
            ::= { sUniCktEntry 2 }


         sUniCktSrcVCI OBJECT-TYPE
             SYNTAX   VCI
             ACCESS   read-only
             STATUS   mandatory
             DESCRIPTION
                "The Data Link Connection Identifier  for  this
                virtual circuit."
           ::= { sUniCktEntry 3 }

         sUniCktAdminDestNode OBJECT-TYPE
             SYNTAX   INTEGER
             ACCESS   read-write
             STATUS   mandatory
             DESCRIPTION
                "The Node Identifier for the Destination
		end of this virtual circuit.
		This variable takes effect when sUniCktSts is set."
            ::= { sUniCktEntry 10 }

         sUniCktOperDestNode OBJECT-TYPE
             SYNTAX   INTEGER
             ACCESS   read-only
             STATUS   mandatory
             DESCRIPTION
                "The Node Identifier for the Destination
		end of this virtual circuit."
            ::= { sUniCktEntry 11 }

         sUniCktAdminDestIfIndex OBJECT-TYPE
             SYNTAX   INTEGER
             ACCESS   read-write
             STATUS   mandatory
             DESCRIPTION
                "The ifIndex Value of the ifEntry this virtual
                circuit is layered onto.  See above comments to
		calculate ifIndex.
		
		This variable takes effect when sUniCktSts is set."
            ::= { sUniCktEntry 12 }


         sUniCktOperDestIfIndex OBJECT-TYPE
             SYNTAX   INTEGER
             ACCESS   read-only
             STATUS   mandatory
             DESCRIPTION
                "The ifIndex Value of the ifEntry this virtual
                circuit is layered onto.  See above comments to
		calculate ifIndex."
            ::= { sUniCktEntry 13 }


         sUniCktAdminDestVCI OBJECT-TYPE
             SYNTAX   VCI
             ACCESS   read-write
             STATUS   mandatory
             DESCRIPTION
                "The Data Link Connection Identifier  for  this
                virtual circuit.
		This variable takes effect when sUniCktSts is set."
           ::= { sUniCktEntry 14 }

         sUniCktOperDestVCI OBJECT-TYPE
             SYNTAX   VCI
             ACCESS   read-only
             STATUS   mandatory
             DESCRIPTION
                "The Data Link Connection Identifier  for  this
                virtual circuit."
           ::= { sUniCktEntry 15 }

 
         sUniCktOperPrinBwType OBJECT-TYPE
             SYNTAX   INTEGER {
		guaranteed (1),
		insured (2)
		}
             ACCESS   read-only
             STATUS   mandatory
             DESCRIPTION
                "This variable indicates the type of service supported
		on primary portion of this Virtual Circuit."
 
                   ::= { sUniCktEntry 22 }

         sUniCktAdminPrinBwType OBJECT-TYPE
             SYNTAX   INTEGER  {
		guaranteed (1),
		insured (2)
		}
             ACCESS   read-write
             STATUS   mandatory
             DESCRIPTION
                "This variable indicates the type of service supported
		on primary portion of this Virtual Circuit.
 
		This variable takes effect when sUniCktSts is set."
 
                   ::= { sUniCktEntry 23 }



         sUniCktOperTransPri OBJECT-TYPE
             SYNTAX   INTEGER  (0..1)
             ACCESS   read-only
             STATUS   mandatory
             DESCRIPTION
                "This variable indicates the transfer priority supported
		on this Virtual Circuit."
 
                   ::= { sUniCktEntry 24 }

         sUniCktAdminTransPri OBJECT-TYPE
             SYNTAX   INTEGER (0..1)
             ACCESS   read-write
             STATUS   mandatory
             DESCRIPTION
                "This variable indicates the transfer priority supported
		on this Virtual Circuit.
 
		This variable takes effect when sUniCktSts is set."
 
                   ::= { sUniCktEntry 25 }

         sUniCktAdminSrcInsuredRate OBJECT-TYPE
             SYNTAX   INTEGER
             ACCESS   read-write
             STATUS   mandatory
             DESCRIPTION
                "This variable, the Insured Rate is the 
		rate of insured data that the network commits
		to supporting under normal network conditions
		from source to destination.

		This is specified in cells per second.
		This variable takes effect when sUniCktSts is set."
           DEFVAL   { 0 }  -- the default indicates no commitment
           ::= { sUniCktEntry 26 }

         sUniCktOperSrcInsuredRate OBJECT-TYPE
             SYNTAX   INTEGER
             ACCESS   read-only
             STATUS   mandatory
             DESCRIPTION
                "This variable, the Insured Rate is the
		rate of insured data that the network commits
		to supporting under normal network conditions
		from source to destination.
		This is specified in cells per second."
           DEFVAL   { 0 }  -- the default indicates no commitment
           ::= { sUniCktEntry 27 }

         sUniCktAdminSrcInsuredBurst OBJECT-TYPE
             SYNTAX   INTEGER
             ACCESS   read-write
             STATUS   mandatory
             DESCRIPTION
                "This variable indicates the Insured Burst 
		Size, which is the amount of insured
                data,  in cells,  that  the  network  agrees to
                transfer under normal  conditions,  during  the
                measurement interval from source to destination.
		This variable takes effect when sUniCktSts is set."
           DEFVAL   { 0 }  -- the default indicates no commitment
           ::= { sUniCktEntry 28 }



         sUniCktOperSrcInsuredBurst OBJECT-TYPE
             SYNTAX   INTEGER
             ACCESS   read-only
             STATUS   mandatory
             DESCRIPTION
                "This variable indicates the Insured Burst 
		Size, which is the amount of insured
                data,  in cells,  that  the  network  agrees to
                transfer under normal  conditions,  during  the
                measurement interval from source to destination."
           DEFVAL   { 0 }  -- the default indicates no commitment
           ::= { sUniCktEntry 29 }



         sUniCktAdminSrcMaxRate OBJECT-TYPE
             SYNTAX   INTEGER
             ACCESS   read-write
             STATUS   mandatory
             DESCRIPTION
                "This variable, the maximum rate is the 
		the total amount of insured plus uninsured
		data throughput that the network attempts
		to support under normal network conditions
		from destination to source.
		This is specified in cells per second.
		This variable takes effect when sUniCktSts is set."
           DEFVAL   { 0 }  -- the default indicates no commitment
           ::= { sUniCktEntry 30 }

         sUniCktOperSrcMaxRate OBJECT-TYPE
             SYNTAX   INTEGER
             ACCESS   read-only
             STATUS   mandatory
             DESCRIPTION
                "This variable, the maximum rate is the 
		the total amount of insured plus uninsured
		data throughput that the network attempts
		to support under normal network conditions
		from destination to source.
		This is specified in cells per second."
           DEFVAL   { 0 }  -- the default indicates no commitment
           ::= { sUniCktEntry 31 }

         sUniCktAdminSrcMaxBurst OBJECT-TYPE
             SYNTAX   INTEGER
             ACCESS   read-write
             STATUS   mandatory
             DESCRIPTION
                "This variable is the maximum Burst Size,
		the maximum amount of insured plus uninsured
                data, in cells, that the network will attempt to deliver 
		over the measurement interval from the Source
		to the Destination.
		This variable takes effect when sUniCktSts is set."
	      DEFVAL   { 0 }  -- the default indicates no commitment
                   ::= { sUniCktEntry 32 }

         sUniCktOperSrcMaxBurst OBJECT-TYPE
             SYNTAX   INTEGER
             ACCESS   read-only
             STATUS   mandatory
             DESCRIPTION
                "This variable indicates the maximum Burst Size,
		the maximum amount of insured plus uninsured
		cells, that the network will attempt to deliver over
		the measurement interval from the Source to the 
		Destination."
	      DEFVAL   { 0 }  -- the default indicates no commitment
                   ::= { sUniCktEntry 33 }

         sUniCktAdminDestInsuredRate OBJECT-TYPE
             SYNTAX   INTEGER
             ACCESS   not-accessible
             STATUS   mandatory
             DESCRIPTION
                "This variable, the Insured Rate is the 
		rate of insured data that the network commits
		to supporting under normal network conditions
		from destination to source.
		This is specified in cells per second.
		This variable takes effect when sUniCktSts is set."
           DEFVAL   { 0 }  -- the default indicates no commitment
           ::= { sUniCktEntry 34 }

         sUniCktOperDestInsuredRate OBJECT-TYPE
             SYNTAX   INTEGER
             ACCESS   read-only
             STATUS   mandatory
             DESCRIPTION
                "This variable, the Insured Rate, is the
		rate of insured data that the network commits
		to supporting under normal network conditions
		from destination to source.
		This is specified in cells per second."
           DEFVAL   { 0 }  -- the default indicates no commitment
           ::= { sUniCktEntry 35 }

         sUniCktAdminDestInsuredBurst OBJECT-TYPE
             SYNTAX   INTEGER
             ACCESS   not-accessible
             STATUS   mandatory
             DESCRIPTION
                "This variable indicates the Insured Burst 
		Size, which is the amount of insured data,
                in cells,  that  the  network  agrees to
                transfer under normal  conditions,  during  the
                measurement interval from destination to source.
		This variable takes effect when sUniCktSts is set."
           DEFVAL   { 0 }  -- the default indicates no commitment
           ::= { sUniCktEntry 36 }



         sUniCktOperDestInsuredBurst OBJECT-TYPE
             SYNTAX   INTEGER
             ACCESS   read-only
             STATUS   mandatory
             DESCRIPTION
                "This variable indicates the Insured Burst 
		Size, which is the amount of insured data,
                in cells,  that  the  network  agrees to
                transfer under normal  conditions,  during  the
                measurement interval from destination to source."
           DEFVAL   { 0 }  -- the default indicates no commitment
           ::= { sUniCktEntry 37 }

         sUniCktAdminDestMaxRate OBJECT-TYPE
             SYNTAX   INTEGER
             ACCESS   not-accessible
             STATUS   mandatory
             DESCRIPTION
                "This variable, the maximum rate is the 
		the total amount of insured plus uninsured
		data throughput that the network attempts
		to support under normal network conditions
		from destination to source.
		This is specified in cells per second.
		This variable takes effect when sUniCktSts is set."
           DEFVAL   { 0 }  -- the default indicates no commitment
           ::= { sUniCktEntry 38 }

         sUniCktOperDestMaxRate OBJECT-TYPE
             SYNTAX   INTEGER
             ACCESS   read-only
             STATUS   mandatory
             DESCRIPTION
                "This variable, the maximum rate is the 
		the total amount of insured plus uninsured
		data throughput that the network attempts
		to support under normal network conditions
		from destination to source.
		This is specified in cells per second."
           DEFVAL   { 0 }  -- the default indicates no commitment
           ::= { sUniCktEntry 39 }

         sUniCktAdminDestMaxBurst OBJECT-TYPE
             SYNTAX   INTEGER
             ACCESS   not-accessible
             STATUS   mandatory
             DESCRIPTION
                "This variable is the maximum Burst Size,
		the maximum amount of insured plus uninsured
		cells that the network will attempt to 
		deliver over the measurement interval from
		the Destination to the Source.

		This variable takes effect when sUniCktSts is set."
           DEFVAL   { 0 }  -- the default indicates no commitment
                   ::= { sUniCktEntry 40 }
 

         sUniCktOperDestMaxBurst OBJECT-TYPE
             SYNTAX   INTEGER
             ACCESS   read-only
             STATUS   mandatory
             DESCRIPTION
                "This variable indicates the maximum Burst Size,
		the maximum amount of insured plus uninsured
		cells that the network will attempt 
		to deliver over the measurement interval
		from the Destination to the Source."
           DEFVAL   { 0 }  -- the default indicates no commitment
                   ::= { sUniCktEntry 41 }
 
	sUniCktAdminSecondaryScale OBJECT-TYPE
           SYNTAX  INTEGER
 	   ACCESS  read-write
           STATUS  mandatory
           DESCRIPTION
            "Secondary bandwidth scaling factor.  This is used to scale
	     down the actual amount of bandwidth to allocate for the 
	     Secondary portion of a VC's bandwidth.   This is specified
	     as a codepoint as follows:

             Codepoints      Meaning         Comment           
	     - ----------    -------         -------           
	                                                       
	     0 - 100         x / 100         e.g., 1 => .01    
	     101 - 109       x - 100 / 1000  e.g., 101 => .001 
	     254             (reserved)      
	     255             (per-port dflt)"
           DEFVAL   { 255 }  -- the default indicates that the port 
			     -- variable should be used
                   ::= { sUniCktEntry 42 }

	sUniCktOperSecondaryScale OBJECT-TYPE
          SYNTAX  INTEGER
	  ACCESS  read-only
          STATUS  mandatory
          DESCRIPTION
            "Operational version of the Secondary bandwidth scaling 
	     factor.  This is used to scale down the actual amount of
	     bandwidth to allocate for the Secondary portion of a VC's
	     bandwidth.   This is specified as a codepoint as follows:

             Codepoints      Meaning         Comment           
	     - ----------    -------         -------           
	                                                       
	     0 - 100         x / 100         e.g., 1 => .01    
	     101 - 109       x - 100 / 1000  e.g., 101 => .001 
	     254             (reserved)      
	     255             (per-port dflt)"
           DEFVAL   { 255 }  -- the default indicates that the port 
			     -- variable should be used
           ::= { sUniCktEntry 43 }

         sUniCktSts OBJECT-TYPE
             SYNTAX   INTEGER {
		enabled (1),
		disabled (2),
		delete (3)
		}
             ACCESS   read-write
             STATUS   mandatory
             DESCRIPTION
                "This variable indicates the Status of this Virtual
		Circuit.  It may be enabled or disabled.  

		In order to modify a Virtual Circuit, the new
		desired variables should be modified and then
		this variable should be set (or set again) to
		enabled.  At that time desired variables will
		become the actual variables.

		To remove a PVC, set its status to delete.
 
                By default, if not configured when creating the
                entry, the status is disabled."
 
                   ::= { sUniCktEntry 99 }

--
     -- Simple (ATM) UNI Circuit Information Table

     -- The table describing the state of the VCIs attached to
     -- each Simple (ATM) UNI Interface.


sUniCktInfoTable OBJECT-TYPE
	SYNTAX	SEQUENCE OF SUniCktInfoEntry
	ACCESS	not-accessible
	STATUS	mandatory
	DESCRIPTION
		"A table containing information about specific VCIs and
                corresponding circuits."
	::= { sUniCktInfo 2 }

sUniCktInfoEntry OBJECT-TYPE
 	SYNTAX	SUniCktInfoEntry
 	ACCESS	not-accessible
 	STATUS	mandatory
 	DESCRIPTION
		"The information regarding a single Data Link
		Connection Identifier."
	INDEX { sUniCktInfoIfIndex, sUniCktInfoVCI }
	::= { sUniCktInfoTable 1 }

SUniCktInfoEntry ::=
	SEQUENCE {
		sUniCktInfoIfIndex
			INTEGER,
 		sUniCktInfoVCI
			VCI,
		sUniCktInfoUniToNetCallID
			INTEGER,
		sUniCktInfoNetToUniCallID
			INTEGER,
		sUniCktInfoUniToNetState
			INTEGER,
		sUniCktInfoNetToUniState
			INTEGER,
		sUniCktInfoLastAtmErr
			OCTET STRING,
		sUniCktInfoLastAtmLocation
			DisplayString (SIZE (0..30)),
	        sUniCktInfoDataCellsRequired
			INTEGER
	}

         sUniCktInfoIfIndex OBJECT-TYPE
             SYNTAX   INTEGER
             ACCESS   read-only
             STATUS   mandatory
             DESCRIPTION
                "The ifIndex Value of the ifEntry this  virtual
                circuit is layered onto.  See above comments to
		calculate ifIndex."
                   ::= { sUniCktInfoEntry 1 }



         sUniCktInfoVCI OBJECT-TYPE
             SYNTAX   VCI
             ACCESS   read-only
             STATUS   mandatory
             DESCRIPTION
                "The Data Link Connection Identifier  for  this
                virtual circuit."
                   ::= { sUniCktInfoEntry 2 }
	--  This call id can be used to access the call progress table and the
	--  line card statistics table.

         sUniCktInfoUniToNetCallID OBJECT-TYPE
             SYNTAX   INTEGER
             ACCESS   read-only
             STATUS   mandatory
             DESCRIPTION
                "This variable indicates the Call Identifier
		assigned to the incomming half of this circuit."
                   ::= { sUniCktInfoEntry 3 }

         sUniCktInfoNetToUniCallID OBJECT-TYPE
             SYNTAX   INTEGER
             ACCESS   read-only
             STATUS   mandatory
             DESCRIPTION
                "This variable indicates the Call Identifier
		assigned to the outgoing half of this circuit."
                   ::= { sUniCktInfoEntry 4 }

         sUniCktInfoUniToNetState OBJECT-TYPE
             SYNTAX   INTEGER {
		active(1),
		inactive(2)
	     }
             ACCESS   read-only
             STATUS   mandatory
             DESCRIPTION
                "This variable indicates the state of the UniToNet
		half of the circuit.  (passing data from the local port
		to the remote end of the network)"
                   ::= { sUniCktInfoEntry 5 }

         sUniCktInfoNetToUniState OBJECT-TYPE
             SYNTAX   INTEGER {
		active(1),
		inactive(2)
	     }
             ACCESS   read-only
             STATUS   mandatory
             DESCRIPTION
                "This variable indicates the state of the NetToUni
		half of the circuit.  (passing data from the port
		at the remote end of the network to the local port)"
                   ::= { sUniCktInfoEntry 6 }


         sUniCktInfoLastAtmErr OBJECT-TYPE
             SYNTAX   OCTET STRING
             ACCESS   read-only
             STATUS   mandatory
             DESCRIPTION
                "This variable indicates the last error, if any,
		returned by the Atm Connection Management layer
		when an attempt was made to create a connection 
		or flow."
                   ::= { sUniCktInfoEntry 7 }

         sUniCktInfoDataCellsRequired OBJECT-TYPE
             SYNTAX   INTEGER
             ACCESS   read-only
             STATUS   mandatory
             DESCRIPTION
                "This variable indicates the bandwidth in
		 cells needed to establish this VC.  The
		 value returned combines the committed and
		 the Secondary bandwidth needs."
                   ::= { sUniCktInfoEntry 8 }

         sUniCktInfoLastAtmLocation OBJECT-TYPE
             SYNTAX   DisplayString (SIZE (0..30))
             ACCESS   read-only
             STATUS   mandatory
             DESCRIPTION
                "This variable indicates the last error, if any,
		returned by the Atm Connection Management layer
		when an attempt was made to create a connection 
		or flow.
		The format of the string is:
		     nodenum:ifIndex
		where all numbers are specified in decimal.  For example
		     5142:6000
		refers to the remote endpoint with node 5142, ifIndex 6000 
		(slot 6 port 0 frType 0)."
                   ::= { sUniCktInfoEntry 9  }

--
--
--
-- Generic Permanent Virtual circuit data
--

    	pvcInfo      OBJECT IDENTIFIER ::= { lsPortProtocols 6 }

     -- A PVC links any endpoints within the network.  If is configured
     -- using two tables.  One table defines the characteristics of the 
     -- circuit itself, such as bandwidth and priority.  The second
     -- defines the remote endpoint(s) location and status.  
     --   Permanent Virtual Circuit Configuration Table
     -- Note that the status for a PVC or a multicast endpoint must
     -- be disabled in order to write to any field.


pvcCfgTable OBJECT-TYPE
	SYNTAX	SEQUENCE OF PvcEntry
	ACCESS	not-accessible
	STATUS	mandatory
	DESCRIPTION
		"A table containing information about specific PVCs."
	::= { pvcInfo 1 }

pvcEntry OBJECT-TYPE
 	SYNTAX	PvcEntry
 	ACCESS	not-accessible
 	STATUS	mandatory
 	DESCRIPTION
		"The information regarding a single PVC."
	INDEX { pvcSrcIfIndex, pvcSrcPvcId }
	::= { pvcCfgTable 1 }

PvcEntry ::=
	SEQUENCE {
		pvcSrcIfIndex
			INTEGER,
 		pvcSrcPvcId
			INTEGER,
		pvcSrcNode
			INTEGER,

		pvcSrcInsuredRate
			INTEGER,
		pvcSrcInsuredBurst
			INTEGER,
		pvcSrcMaxRate
			INTEGER,
		pvcSrcMaxBurst
			INTEGER,

		pvcSecondaryScale
			INTEGER,
		pvcPrinBwType
			INTEGER,
		pvcTransPri
			INTEGER,
     	    	pvcUserDataPerCell
                        INTEGER,
		pvcStatus
			INTEGER
	}
 
         pvcSrcIfIndex OBJECT-TYPE
             SYNTAX   INTEGER
             ACCESS   read-only
             STATUS   mandatory
             DESCRIPTION
                "The ifIndex Value of the ifEntry this  virtual
                circuit is layered onto.  See above comments to
		calculate ifIndex."
            ::= { pvcEntry 1 }


         pvcSrcPvcId OBJECT-TYPE
             SYNTAX   INTEGER
             ACCESS   read-only
             STATUS   mandatory
             DESCRIPTION
                "The local PVC Connection Identifier for this
                 virtual circuit."
            REFERENCE
               "Draft American National  Standard  T1.618-1991,
               Section 3.3.6"
           ::= { pvcEntry 2 }

         pvcSrcNode OBJECT-TYPE
             SYNTAX   INTEGER
             ACCESS   read-only
             STATUS   mandatory
             DESCRIPTION
                "The Node Identifier for the source
		end of this virtual circuit."
            ::= { pvcEntry 3 }

         pvcSrcInsuredRate OBJECT-TYPE
             SYNTAX   INTEGER
             ACCESS   read-write
             STATUS   mandatory
             DESCRIPTION
                "This variable, the Insured Rate is the
		rate of insured data that the network commits
		to supporting under normal network conditions
		from Source to Destination.
		It is specified in bits per second.
		This variable takes effect when pvcStatus is set.
		This variable may not be modified unless pvcStatus
                is set to disabled."
            REFERENCE
               "Draft American National  Standard  T1.617-1991,
               Section 6.5.19 Throughput parameter"
           DEFVAL   { 0 }  -- the default indicates no commitment
           ::= { pvcEntry 4 }

         pvcSrcInsuredBurst OBJECT-TYPE
             SYNTAX   INTEGER
             ACCESS   read-write
             STATUS   mandatory
             DESCRIPTION
                "This variable indicates the Insured Burst 
		Size, which is the amount of insured data,
                in  bytes,  that  the  network  agrees to
                transfer under normal  conditions,  during  the
                measurement interval from source to destination.
		This variable takes effect when pvcStatus is set.
		This variable may not be modified unless pvcStatus
                is set to disabled."
            REFERENCE
               "Draft American National  Standard  T1.617-1991,
               Section 6.5.19"
           DEFVAL   { 0 }  -- the default indicates no commitment
           ::= { pvcEntry 5 }



         pvcSrcMaxRate OBJECT-TYPE
             SYNTAX   INTEGER
             ACCESS   read-write
             STATUS   mandatory
             DESCRIPTION
                "This variable, the Maximum Rate is the 
		the maximum amount of insured plus uninsured
		data throughput that the network agrees
		to support from source to destination.
		It is specified in bits per second.
		This variable takes effect when pvcStatus is set.
		This variable may not be modified unless pvcStatus
                is set to disabled."
            REFERENCE
               "Draft American National  Standard  T1.617-1991,
               Section 6.5.19 Throughput parameter"
           DEFVAL   { 0 }  -- the default indicates no commitment
           ::= { pvcEntry 6 }

         pvcSrcMaxBurst OBJECT-TYPE
             SYNTAX   INTEGER
             ACCESS   read-write
             STATUS   mandatory
             DESCRIPTION
                "This variable indicates the Total Burst Size,
		which is the maximum amount of insured plus
                uninsured data bytes that the network will at-
                tempt to deliver over the measurement interval
		from the Source to the Destination.

		This variable takes effect when pvcStatus is set.
		This variable may not be modified unless pvcStatus
                is set to disabled."
            REFERENCE
               "Draft American National  Standard  T1.617-1991,
               Section 6.5.19"
           DEFVAL   { 0 }  -- the default indicates no commitment
                   ::= { pvcEntry 7 }

	pvcSecondaryScale OBJECT-TYPE
           SYNTAX  INTEGER
 	   ACCESS  read-write
           STATUS  mandatory
           DESCRIPTION
            "Secondary bandwidth scaling factor.  This is used to scale
	     down the actual amount of bandwidth to allocate for the 
	     Secondary portion of a VC's bandwidth.   This is specified
	     as a codepoint as follows:

             Codepoints      Meaning         Comment           
	     - ----------    -------         -------           
	                                                       
	     0 - 100         x / 100         e.g., 1 => .01    
	     101 - 109       x - 100 / 1000  e.g., 101 => .001 
	     254             (reserved)      
	     255             (per-port dflt)"
           DEFVAL   { 255 }  -- the default indicates that the port 
			     -- variable should be used
                   ::= { pvcEntry 8 }

         pvcPrinBwType OBJECT-TYPE
             SYNTAX   INTEGER  {
		guaranteed (1),
		insured (2)
		}
             ACCESS   read-write
             STATUS   mandatory
             DESCRIPTION
                "This variable indicates the type of service supported
		on primary portion of this Virtual Circuit.
 
		This variable takes effect when pvcStatus is set.
		This variable may not be modified unless pvcStatus
                is set to disabled."
	    DEFVAL   { 1 }  -- use Insured by default
                    ::= { pvcEntry 9 }

         pvcTransPri OBJECT-TYPE
             SYNTAX   INTEGER (0..1)
             ACCESS   read-write
             STATUS   mandatory
             DESCRIPTION
                "This variable indicates the transfer priority supported
		on this Virtual Circuit.
 
		This variable takes effect when pvcStatus is set.
		This variable may not be modified unless pvcStatus
                is set to disabled."
	    DEFVAL   { 0 }  -- use priority DG0 by default
                    ::= { pvcEntry 10 }

         pvcUserDataPerCell OBJECT-TYPE
              SYNTAX  INTEGER ( 0..384 )
    	      ACCESS  read-write
              STATUS  mandatory
              DESCRIPTION
                  "User data bits per cell, specifies the expected
		   packing efficiency  when frames are converted to cells.
		   It does not affect the actual packing of data into cells
		   but serves as an estimate on which bandwidth allocation
		   and other connection related functions will be based.
 
		   This variable takes effect when pvcStatus is set.
		This variable may not be modified unless pvcStatus
                is set to disabled."
	      DEFVAL   { 0 }  -- the default indicates that the port 
			     -- variable should be used
              ::= { pvcEntry 11 }

         pvcStatus OBJECT-TYPE
             SYNTAX   INTEGER {
		enabled (1),
		disabled (2),
		delete (3)
		}
             ACCESS   read-write
             STATUS   mandatory
             DESCRIPTION
                "This variable indicates the Status of this Virtual
		Circuit.  It may be enabled or disabled.  

		In order to modify a Virtual Circuit, the new
		desired variables should be modified and then
		this variable should be set (or set again) to
		enabled.  At that time desired variables will
		become the actual variables.

		To remove a PVC, set its status to delete.
 
                By default, if not configured when creating the
                entry, the status is disabled."
 
                   ::= { pvcEntry 99 }

--
-- Generic Multicast Endpoint data
--

    	mcEndptInfo      OBJECT IDENTIFIER ::= { lsPortProtocols 7 }

mcEndptCfgTable OBJECT-TYPE
	SYNTAX	SEQUENCE OF McEndptEntry
	ACCESS	not-accessible
	STATUS	mandatory
	DESCRIPTION
		"A table containing information about specific endpoints and
                corresponding circuits."
	::= { mcEndptInfo 1 }

mcEndptEntry OBJECT-TYPE
 	SYNTAX	McEndptEntry
 	ACCESS	not-accessible
 	STATUS	mandatory
 	DESCRIPTION
		"The information regarding a single endpoint."
	INDEX { mcEndptLclIfIndex, mcEndptLclCktid, mcEndptLclInstance }
	::= { mcEndptCfgTable 1 }

McEndptEntry ::=
	SEQUENCE {
		mcEndptLclIfIndex
			INTEGER,
 		mcEndptLclCktid
			INTEGER,
		mcEndptLclInstance
			INTEGER,
		mcEndptDest
			DisplayString (SIZE (0..30)),
		mcEndptServiceType
			INTEGER,
		mcEndptRmtVCstatus
			INTEGER,
		mcEndptCallIDIncoming
			INTEGER,
		mcEndptDownstreamState
			INTEGER,
		mcEndptUpstreamState
			INTEGER,
		mcEndptLastAtmErr
			OCTET STRING,
		mcEndptLastAtmLocation
			DisplayString (SIZE (0..30)),
		mcEndptStatus
			INTEGER
	}


         mcEndptLclIfIndex OBJECT-TYPE
             SYNTAX   INTEGER
             ACCESS   read-only
             STATUS   mandatory
             DESCRIPTION
                "The ifIndex Value of the ifEntry this virtual
                circuit is layered onto.  See above comments to
		calculate ifIndex."
            ::= { mcEndptEntry 1 }

         mcEndptLclCktid OBJECT-TYPE
             SYNTAX   INTEGER
             ACCESS   read-only
             STATUS   mandatory
             DESCRIPTION
                "The Local Circuit Identifier  for  this virtual circuit."
           ::= { mcEndptEntry 2 }

         mcEndptLclInstance OBJECT-TYPE
             SYNTAX   INTEGER
             ACCESS   read-only
             STATUS   mandatory
             DESCRIPTION
                "A Locally significant index used to separate the 
		 different remote endpoints for this multicast virtual 
		 circuit."
           ::= { mcEndptEntry 3 }

         mcEndptDest OBJECT-TYPE
             SYNTAX   DisplayString (SIZE (0..30))
             ACCESS   read-write
             STATUS   mandatory
             DESCRIPTION
                "The Destination for this segment of the multicast virtual
		 circuit.  The format of the string is:
		     nodenum:ifIndex:cktID
		where all numbers are specified in decimal.  For example
		     5142:6000:16
		refers to the remote endpoint with node 5142, ifIndex 6000 
		(slot 6 port 0 frType 0), and circuit identifier 16.

		This variable cannot be modified while mcEndptStatus is 
		set to active."
            ::= { mcEndptEntry 4 }

         mcEndptServiceType OBJECT-TYPE
             SYNTAX   INTEGER
             ACCESS   read-write
             STATUS   mandatory
             DESCRIPTION
                "This variable is provided for future expansion,
		 to allow creation of VCs between dissimilar 
		 protocols.

		This variable cannot be modified while mcEndptStatus is 
		set to active."
            ::= { mcEndptEntry 5 }

         mcEndptRmtVCstatus OBJECT-TYPE
             SYNTAX   INTEGER {
		active(1),
		inactive(2)
	     }
             ACCESS   read-only
             STATUS   mandatory
             DESCRIPTION
                "This variable indicates the remote state of the circuit.
		 For FR this would be the LMI status."
             ::= { mcEndptEntry 6 }


         mcEndptCallIDIncoming OBJECT-TYPE
             SYNTAX   INTEGER
             ACCESS   read-only
             STATUS   mandatory
             DESCRIPTION
                "This variable indicates the Call Identifier assigned to
		 the incomming (from the net) direction of this circuit."
                   ::= { mcEndptEntry 7 }

         mcEndptDownstreamState OBJECT-TYPE
             SYNTAX   INTEGER {
		active(1),
		inactive(2)
	     }
             ACCESS   read-only
             STATUS   mandatory
             DESCRIPTION
                "This variable indicates the state of the downstream
		direction of the circuit.  (passing data from the local
		port to the remote end of the network)"
                   ::= { mcEndptEntry 8 }

         mcEndptUpstreamState OBJECT-TYPE
             SYNTAX   INTEGER {
		active(1),
		inactive(2)
	     }
             ACCESS   read-only
             STATUS   mandatory
             DESCRIPTION
                "This variable indicates the state of the upstream
		direction of the circuit.  (passing data from the port
		at the remote end of the network to the local port)"
                   ::= { mcEndptEntry 9 }

         mcEndptLastAtmErr OBJECT-TYPE
             SYNTAX   OCTET STRING 
             ACCESS   read-only
             STATUS   mandatory
             DESCRIPTION
                "This variable indicates the last error, if any,
		returned by the Atm Connection Management layer
		when an attempt was made to create a connection 
		or flow."
                   ::= { mcEndptEntry 10  }

         mcEndptLastAtmLocation OBJECT-TYPE
             SYNTAX   DisplayString (SIZE (0..30))
             ACCESS   read-only
             STATUS   mandatory
             DESCRIPTION
                "This variable indicates the last error, if any,
		returned by the Atm Connection Management layer
		when an attempt was made to create a connection 
		or flow.
		The format of the string is:
		     nodenum:ifIndex
		where all numbers are specified in decimal.  For example
		     5142:6000
		refers to the remote endpoint with node 5142, ifIndex 6000 
		(slot 6 port 0 frType 0)."
                   ::= { mcEndptEntry 11  }

         mcEndptStatus OBJECT-TYPE
             SYNTAX   INTEGER {
		enabled (1),
		disabled (2),
		delete (3),
		createRequest (4),
		underCreation (5)
		}
             ACCESS   read-write
             STATUS   mandatory
             DESCRIPTION
                "This variable indicates the Status of this Virtual
		Circuit.  It may be enabled or disabled.  

		In order to modify a Virtual Circuit, the new
		desired variables should be modified and then
		this variable should be set (or set again) to
		enabled.  At that time desired variables will
		become the operational (or in-use) variables.

		To remove a PVC, set its status to delete.

		By default, if not configured when creating the
		entry, the status is disabled.

		An existing instance of this object cannot be set to
		createRequest(4).  This object may only be set to
		createRequest(4) when this instance is created.  When
		this object is created, the agent may wish to create
		supplemental object instances to complete a conceptual
		row in this table.  Immediately after completing the
		create operation, the agent must set this object to
		underCreation(5).

		Entries shall exist in the underCreation(5) state until
		the management station is finished configuring the
		entry and sets this object to active(1), inactive(2),
		or aborts, setting this object to delete(4).  If the 
		agent determines that an entry has been in the
		underCreation(5) state for an abnormally long time,
		it may decide that the management station has
		become unavailable.  If the agent makes this decision,
		it may set this object to delete(3) to reclaim the
		entry.  A prudent agent will understand that the
		management station may need to wait for human input
		and will allow for that possibility in its
		determination of this abnormally long period."

                   ::= { mcEndptEntry 99 }



--
--
-- Private (Reserved for later releases 
--
         lsPrivate              OBJECT IDENTIFIER ::= { atmSwitch 10 }

--
--
-- Experimental
-- (Stats are kept here for the time being)
--

         lsExperimental         OBJECT IDENTIFIER ::= { atmSwitch 11 }

-- Statistics Extensions.  (Tentative)
 
-- Note that configuration definitions and other data items are also needed
-- (for instance, Permit block, Smoother parameters, circuit to port/vci maps,
-- among others.
 
      lsExperimentalStatistics OBJECT IDENTIFIER ::= { lsExperimental 1 }
 
-- 	EDGE SPECIFIC STATISTICS SUBSET

	 lsEdgeStatistics OBJECT IDENTIFIER ::= { lsExperimentalStatistics 1 }
 
-- Statistics associated with each Edge card on a per-Edge card basis

         lsEdgeStatTable OBJECT-TYPE
    	   SYNTAX  SEQUENCE OF LsEdgeStatEntry
           ACCESS  not-accessible
	   STATUS  mandatory
	   DESCRIPTION
               "Edge Card specific statistics subset information"
	   ::= { lsEdgeStatistics 1 }

	 lsEdgeStatEntry OBJECT-TYPE
	   SYNTAX   LsEdgeStatEntry
	   ACCESS   not-accessible
	   STATUS   mandatory
	   DESCRIPTION
	       "An entry in Edge Card Statistics Table."
	   INDEX   { edgeStatIndex }
	   ::= { lsEdgeStatTable 1 }

	 LsEdgeStatEntry ::=
	   SEQUENCE {
	       edgeStatIndex
	       	INTEGER,
	       edgeStatFsuRATOs
	       	Counter,
	       edgeStatFsuRATOLastInfo
	       	INTEGER,
	       edgeStatTsuHoldQCells
	       	Gauge,
	       edgeStatTsuHoldQs
	       	Gauge,
	       tluAAL5XsumErrs
	       	Counter,
	       tluAAL5AbortErrs
	       	Counter,
	       tluAAL5ErrLastVci
	       	INTEGER
	       }
    	       	    
  edgeStatIndex OBJECT-TYPE
      SYNTAX  INTEGER
      ACCESS  read-only
      STATUS  mandatory
      DESCRIPTION
          "This is the ifIndex value of the corresponding
	  ifEntry.  See comments above."
  ::= { lsEdgeStatEntry 1 }

  edgeStatFsuRATOs OBJECT-TYPE
      SYNTAX  Counter
      ACCESS  read-only
      STATUS  mandatory
      DESCRIPTION
          "The total number of Reassembly TimeOuts detected by the FSU"
  ::= { lsEdgeStatEntry 2 }

  edgeStatFsuRATOLastInfo OBJECT-TYPE
      SYNTAX  INTEGER
      ACCESS  read-only
      STATUS  mandatory
      DESCRIPTION
          "Header Information related to the last RATO (Port/VCI minimum)"
  ::= { lsEdgeStatEntry 3 }

  edgeStatTsuHoldQCells OBJECT-TYPE
      SYNTAX  Gauge
      ACCESS  read-only
      STATUS  mandatory
      DESCRIPTION
          "The total number of cells in hold queues"
  ::= { lsEdgeStatEntry 4 }


  edgeStatTsuHoldQs OBJECT-TYPE
      SYNTAX  Gauge
      ACCESS  read-only
      STATUS  mandatory
      DESCRIPTION
          "The total number of active hold queues"
  ::= { lsEdgeStatEntry 5 }

 -- The following may be ASIC dependent

  tluAAL5XsumErrs OBJECT-TYPE
      SYNTAX  Counter
      ACCESS  read-only
      STATUS  mandatory
      DESCRIPTION
          "Number of AAL5 Xsum errors detected by the TLU.
           Availability may depend on HW type, such as ASIC HW."
  ::= { lsEdgeStatEntry 6 }

  tluAAL5AbortErrs OBJECT-TYPE
      SYNTAX  Counter
      ACCESS  read-only
      STATUS  mandatory
      DESCRIPTION
          "Number of AAL5 Abort errors (zero length) detected by the TLU.
           Availability may depend on HW type, such as ASIC HW."
  ::= { lsEdgeStatEntry 7 }

  tluAAL5ErrLastVci OBJECT-TYPE
      SYNTAX  INTEGER
      ACCESS  read-only
      STATUS  mandatory
      DESCRIPTION
          "Contains the 16-bit VCI index corresponding to the last AAL5
           Xsum or Abort error, along with the port number.  Format TBD.
           Availability may depend on HW type, such as ASIC HW."
  ::= { lsEdgeStatEntry 8 }


 -- Statistics associated with each Edge Port on a per-Edge Port basis
  lsEdgePortStatTable OBJECT-TYPE
    SYNTAX  SEQUENCE OF LsEdgePortStatEntry
    ACCESS  not-accessible
    STATUS  mandatory
    DESCRIPTION
        "Edge Card specific statistics subset information"
    ::= { lsEdgeStatistics 2 }

  lsEdgePortStatEntry OBJECT-TYPE
    SYNTAX   LsEdgePortStatEntry
    ACCESS   not-accessible
    STATUS   mandatory
    DESCRIPTION
        "An entry in Edge Port Statistics Table."
    INDEX   { edgePortStatIndex }
    ::= { lsEdgePortStatTable 1 }

  LsEdgePortStatEntry ::=
    SEQUENCE {
        edgePortStatIndex
        	INTEGER,
        edgePortRcvOctets
        	Counter,
        edgePortXmtOctets
        	Counter,
        edgePortFsuCksmErrMsgs
        	Counter,
        edgePortCksmErrLastVci
        	INTEGER,
        edgePortDownXmtFrames
        	Counter,

 	-- The following may be specific to ASIC HW
        edgePortRcvUcastPkts
        	Counter,
        edgePortRcvNUcastPkts
        	Counter,
        edgePortXmtUcastPkts
        	Counter,
        edgePortXmtNUcastPkts
        	Counter,
        edgePortRcvSmplPktSize
          Gauge,
        edgePortXmtSmplPktSize
          Gauge,
        edgePortRcvL3XsumErrs
        	Counter,
        edgePortRcvL3XsumErrLastVci
        	INTEGER,

 	-- The following are essentially L2 errors and may need
         -- to go somewhere else.  These errors derive from I/O
 	-- hardware, and may duplicate information in another portion
 	-- of the MIB.  Likely to be incomplete.
        edgePortRcvCRCErrors
        	Counter,
        edgePortRcvAborts
        	Counter,
        edgePortXmtUnderflows
        	Counter,
        edgePortRcvShortFrames
        	Counter
        }
        	    
  edgePortStatIndex OBJECT-TYPE
      SYNTAX  INTEGER
      ACCESS  read-only
      STATUS  mandatory
      DESCRIPTION
                  "This is the ifIndex value of the corresponding
		  ifEntry.  See comments above."
  ::= { lsEdgePortStatEntry 1 }

  edgePortRcvOctets OBJECT-TYPE
      SYNTAX  Counter
      ACCESS  read-only
      STATUS  mandatory
      DESCRIPTION
          "Number of octets received regardless of error status"
  ::= { lsEdgePortStatEntry 2 }

  edgePortXmtOctets OBJECT-TYPE
      SYNTAX  Counter
      ACCESS  read-only
      STATUS  mandatory
      DESCRIPTION
          "Number of octets transmitted regardless of error status"
  ::= { lsEdgePortStatEntry 3 }

  edgePortFsuCksmErrMsgs OBJECT-TYPE
      SYNTAX  Counter
      ACCESS  read-only
      STATUS  mandatory
      DESCRIPTION
          "The number of messages with AAL5 checksum errors detected by FSU.
           May not be provided on a per-port basis in all HW."
  ::= { lsEdgePortStatEntry 4 }

  edgePortCksmErrLastVci OBJECT-TYPE
      SYNTAX  INTEGER
      ACCESS  read-only
      STATUS  mandatory
      DESCRIPTION
          "The last Vci index associated with a AAL5 checksum error.
           May not be provided on a per-port basis in all HW."
  ::= { lsEdgePortStatEntry 5 }

  edgePortDownXmtFrames OBJECT-TYPE
      SYNTAX  Counter
      ACCESS  read-only
      STATUS  mandatory
      DESCRIPTION
          "The number of messages received by the TSU for which the
           the VCI was not configured."
  ::= { lsEdgePortStatEntry 6 }


 -- The following may be ASIC HW dependent 

  edgePortRcvUcastPkts OBJECT-TYPE
      SYNTAX  Counter
      ACCESS  read-only
      STATUS  mandatory
      DESCRIPTION
          "Number of Unicast packets received.
           Availability may depend on HW type, such as ASIC HW."
  ::= { lsEdgePortStatEntry 7 }

  edgePortRcvNUcastPkts OBJECT-TYPE
      SYNTAX  Counter
      ACCESS  read-only
      STATUS  mandatory
      DESCRIPTION
          "Number of Non-Unicast packets received.
           Availability may depend on HW type, such as ASIC HW."
  ::= { lsEdgePortStatEntry 8 }

  edgePortXmtUcastPkts OBJECT-TYPE
      SYNTAX  Counter
      ACCESS  read-only
      STATUS  mandatory
      DESCRIPTION
          "Number of Unicast packets transmitted.
           Availability may depend on HW type, such as ASIC HW."
  ::= { lsEdgePortStatEntry 9 }

  edgePortXmtNUcastPkts OBJECT-TYPE
      SYNTAX  Counter
      ACCESS  read-only
      STATUS  mandatory
      DESCRIPTION
          "Number of Non-Unicast packets transmitted.
           Availability may depend on HW type, such as ASIC HW."
  ::= { lsEdgePortStatEntry 10 }

  edgePortRcvSmplPktSize OBJECT-TYPE
      SYNTAX  Gauge
      ACCESS  read-only
      STATUS  mandatory
      DESCRIPTION
          "Number of octets for the last sampled from-port packet, including
           overhead octets.  Used as a substitute for the frame size histogram
           when the histogram is not available.  Availability may depend on
           HW type, such as ASIC HW.

           Sampling algorithm to be determined."
  ::= { lsEdgePortStatEntry 11 }

  edgePortXmtSmplPktSize OBJECT-TYPE
      SYNTAX  Gauge
      ACCESS  read-only
      STATUS  mandatory
      DESCRIPTION
          "Number of octets for the last sampled to-port packet, including
           overhead octets.  Used as a substitute for the frame size histogram
           when the histogram is not available.  Availability may depend on
           HW type, such as ASIC HW.

          Sampling algorithm to be determined."
  ::= { lsEdgePortStatEntry 12 }

  edgePortRcvL3XsumErrs OBJECT-TYPE
      SYNTAX  Counter
      ACCESS  read-only
      STATUS  mandatory
      DESCRIPTION
          "Number of L3 packets processed with a Level 3 checksum error.
           Availability may depend on HW type, such as ASIC HW."
  ::= { lsEdgePortStatEntry 13 }

  edgePortRcvL3XsumErrLastVci OBJECT-TYPE
      SYNTAX  INTEGER
      ACCESS  read-only
      STATUS  mandatory
      DESCRIPTION
          "Last 15-bit VCI index associated with a Level 3 checksum error.
           Availability may depend on HW type, such as ASIC HW."
  ::= { lsEdgePortStatEntry 14 }

 -- Begin L2 error Definitions.  May want to put elsewhere or in
 -- separate table.
  edgePortRcvCRCErrors OBJECT-TYPE
      SYNTAX  Counter
      ACCESS  read-only
      STATUS  mandatory
      DESCRIPTION
          "The number of messages received by the port with CRC errors."
  ::= { lsEdgePortStatEntry 15 }

  edgePortRcvAborts OBJECT-TYPE
      SYNTAX  Counter
      ACCESS  read-only
      STATUS  mandatory
      DESCRIPTION
          "The number of aborts detected by the HW."
  ::= { lsEdgePortStatEntry 16 }


  edgePortXmtUnderflows OBJECT-TYPE
      SYNTAX  Counter
      ACCESS  read-only
      STATUS  mandatory
      DESCRIPTION
          "The number of underflow events detected by I/O hardware."
  ::= { lsEdgePortStatEntry 17 }


  edgePortRcvShortFrames OBJECT-TYPE
      SYNTAX  Counter
      ACCESS  read-only
      STATUS  mandatory
      DESCRIPTION
          "The number of short incoming frames detected by L2"
  ::= { lsEdgePortStatEntry 18 }


 -- FrameRelay statistics specific to port and DLCI
 -- Double indexing permits us to condition DLCI interpretation on the port.

  lsFrameRelayDlciStatTable OBJECT-TYPE
    SYNTAX  SEQUENCE OF LsFrameRelayDlciStatEntry
    ACCESS  not-accessible
    STATUS  mandatory
    DESCRIPTION
        "FrameRelay Port/DLCI specific statistics subset information"
    ::= { lsEdgeStatistics 3 }

  lsFrameRelayDlciStatEntry OBJECT-TYPE
    SYNTAX   LsFrameRelayDlciStatEntry
    ACCESS   not-accessible
    STATUS   mandatory
    DESCRIPTION
        "An entry in the FrameRelay Port/Dlci Statistics Table."
    INDEX   { frameRelayDlciStatPortIndex, frameRelayDlciStatDlciIndex }
    ::= { lsFrameRelayDlciStatTable 1 }

  LsFrameRelayDlciStatEntry ::=
    SEQUENCE {
        frameRelayDlciStatPortIndex
        	INTEGER,
        frameRelayDlciStatDlciIndex
        	INTEGER,
        frameRelayDlciToSwCLP0Frames
        	Counter,
        frameRelayDlciToSwCLP0Cells
        	Counter,
        frameRelayDlciToSwCLP1Frames
        	Counter,
        frameRelayDlciToSwCLP1Cells
        	Counter,
        frameRelayDlciToSwDiscardFrames
        	Counter,
        frameRelayDlciToSwDiscardCells
        	Counter,
        frameRelayDlciFrSwCLP0Frames
        	Counter,
        frameRelayDlciFrSwCLP0Cells
        	Counter,
        frameRelayDlciFrSwCLP1Frames
        	Counter,
        frameRelayDlciFrSwCLP1Cells
        	Counter
        }

        	    
  frameRelayDlciStatPortIndex OBJECT-TYPE
      SYNTAX  INTEGER
      ACCESS  read-only
      STATUS  mandatory
      DESCRIPTION
                  "This is the ifIndex value of the corresponding
		  ifEntry.  See comments above."
  ::= { lsFrameRelayDlciStatEntry 1 }


  frameRelayDlciStatDlciIndex OBJECT-TYPE
      SYNTAX  INTEGER
      ACCESS  read-only
      STATUS  mandatory
      DESCRIPTION
          "Unique Dlci identifier for indicated port"
  ::= { lsFrameRelayDlciStatEntry 2 }


  frameRelayDlciToSwCLP0Frames OBJECT-TYPE
      SYNTAX  Counter
      ACCESS  read-only
      STATUS  mandatory
      DESCRIPTION
          "Number of Frames forwarded to TSU with CLP=0"
  ::= { lsFrameRelayDlciStatEntry 3 }

  frameRelayDlciToSwCLP0Cells OBJECT-TYPE
      SYNTAX  Counter
      ACCESS  read-only
      STATUS  mandatory
      DESCRIPTION
          "Number of Cells forwarded to TSU with CLP=0"
  ::= { lsFrameRelayDlciStatEntry 4 }


  frameRelayDlciToSwCLP1Frames OBJECT-TYPE
      SYNTAX  Counter
      ACCESS  read-only
      STATUS  mandatory
      DESCRIPTION
          "Number of Frames forwarded to TSU with CLP=1"
  ::= { lsFrameRelayDlciStatEntry 5 }

  frameRelayDlciToSwCLP1Cells OBJECT-TYPE
      SYNTAX  Counter
      ACCESS  read-only
      STATUS  mandatory
      DESCRIPTION
          "Number of Cells forwarded to TSU with CLP=1"
  ::= { lsFrameRelayDlciStatEntry 6 }

  frameRelayDlciToSwDiscardFrames OBJECT-TYPE
      SYNTAX  Counter
      ACCESS  read-only
      STATUS  mandatory
      DESCRIPTION
          "Number of to-switch Frames discarded due to excessive traffic
 	  according to the Usage Parameter Descriptor for this Dlci"
  ::= { lsFrameRelayDlciStatEntry 7 }

  frameRelayDlciToSwDiscardCells OBJECT-TYPE
      SYNTAX  Counter
      ACCESS  read-only
      STATUS  mandatory
      DESCRIPTION
          "Number of to-switch Cells discarded due to excessive traffic
 	  according to the Usage Parameter Descriptor for this Dlci"
  ::= { lsFrameRelayDlciStatEntry 8 }

  frameRelayDlciFrSwCLP0Frames OBJECT-TYPE
      SYNTAX  Counter
      ACCESS  read-only
      STATUS  mandatory
      DESCRIPTION
          "Number of frames received from the switch with CLP=0"
  ::= { lsFrameRelayDlciStatEntry 9 }

  frameRelayDlciFrSwCLP0Cells OBJECT-TYPE
      SYNTAX  Counter
      ACCESS  read-only
      STATUS  mandatory
      DESCRIPTION
          "Number of cells received from the switch with CLP=0"
  ::= { lsFrameRelayDlciStatEntry 10 }


  frameRelayDlciFrSwCLP1Frames OBJECT-TYPE
      SYNTAX  Counter
      ACCESS  read-only
      STATUS  mandatory
      DESCRIPTION
          "Number of frames received from the switch with CLP=1"
  ::= { lsFrameRelayDlciStatEntry 11 }

  frameRelayDlciFrSwCLP1Cells OBJECT-TYPE
      SYNTAX  Counter
      ACCESS  read-only
      STATUS  mandatory
      DESCRIPTION
          "Number of cells received from the switch with CLP=1"
  ::= { lsFrameRelayDlciStatEntry 12 }


 
-- Edge statistics for obtaining a distribution of message lengths
-- indexed by port and length bin indices.  Sizes are in units of cells
-- after adaption has taken place.

-- To Switch message length histogram, based on cell size after any
-- header operations, for good incoming or outgoing frames.  These may not
-- be available with the ASIC versions.
 
      -- Incoming message length histogram (Port to Switch)
 
         lsEdgePortToSwMsgLenTable OBJECT-TYPE
    	   SYNTAX  SEQUENCE OF LsEdgePortToSwMsgLenEntry
           ACCESS  not-accessible
	   STATUS  mandatory
	   DESCRIPTION
               "Histogram of incoming message lengths (in cells) by Edge port"
         ::= { lsEdgeStatistics	4 }

         lsEdgePortToSwMsgLenEntry OBJECT-TYPE
	   SYNTAX   LsEdgePortToSwMsgLenEntry
	   ACCESS   not-accessible
	   STATUS   mandatory
	   DESCRIPTION
	       "An entry in the Edge Port/Incoming-Message-Cell-Length
	        histogram table."
	   INDEX   { edgeToSwMsgLenPortIndex, edgeToSwMsgLenBinIndex }
	   ::= { lsEdgePortToSwMsgLenTable 1 }

	 LsEdgePortToSwMsgLenEntry ::=
	   SEQUENCE {
	       edgeToSwMsgLenPortIndex
	       	INTEGER,
	       edgeToSwMsgLenBinIndex
	       	INTEGER,
	       edgeToSwMsgLenMsgs
	       	Counter
	       }
 
         edgeToSwMsgLenPortIndex OBJECT-TYPE
             SYNTAX  INTEGER
    	     ACCESS  read-only
             STATUS  mandatory
             DESCRIPTION
                  "This is the ifIndex value of the corresponding
		  ifEntry.  See comments above."
	   ::= { lsEdgePortToSwMsgLenEntry 1 }

         edgeToSwMsgLenBinIndex OBJECT-TYPE
             SYNTAX  INTEGER
    	     ACCESS  read-only
             STATUS  mandatory
             DESCRIPTION
                 "Histogram index for the incoming message size in units of
		  network cells"
	   ::= { lsEdgePortToSwMsgLenEntry 2 }

         edgeToSwMsgLenMsgs OBJECT-TYPE
             SYNTAX  Counter
    	     ACCESS  read-only
             STATUS  mandatory
             DESCRIPTION
                 "Count of the number of incoming messages of the given
                  length in units of network cells."
	   ::= { lsEdgePortToSwMsgLenEntry 3 }

      -- Outgoing message length histogram (Switch to Port)
 
         lsEdgeSwToPortMsgLenTable OBJECT-TYPE
    	   SYNTAX  SEQUENCE OF LsEdgeSwToPortMsgLenEntry
           ACCESS  not-accessible
	   STATUS  mandatory
	   DESCRIPTION
               "Histogram of incoming message lengths (in cells) by Edge port"
         ::= { lsEdgeStatistics	5 }

    	   lsEdgeSwToPortMsgLenEntry OBJECT-TYPE
	   SYNTAX   LsEdgeSwToPortMsgLenEntry
	   ACCESS   not-accessible
	   STATUS   mandatory
	   DESCRIPTION
	       "An entry in the Edge Port/Outgoing-Message-Cell-Length
	        histogram table."
	   INDEX   { edgeToPortMsgLenPortIndex, edgeToPortMsgLenBinIndex }
	   ::= { lsEdgeSwToPortMsgLenTable 1 }

	 LsEdgeSwToPortMsgLenEntry ::=
	   SEQUENCE {
	       edgeToPortMsgLenPortIndex
	       	INTEGER,
	       edgeToPortMsgLenBinIndex
	       	INTEGER,
	       edgeToPortMsgLenMsgs
	       	Counter
	       }
 
         edgeToPortMsgLenPortIndex OBJECT-TYPE
             SYNTAX  INTEGER
    	     ACCESS  read-only
             STATUS  mandatory
             DESCRIPTION
                  "This is the ifIndex value of the corresponding
		  ifEntry.  See comments above."
	   ::= { lsEdgeSwToPortMsgLenEntry 1 }

         edgeToPortMsgLenBinIndex OBJECT-TYPE
             SYNTAX  INTEGER
    	     ACCESS  read-only
             STATUS  mandatory
             DESCRIPTION
                 "Histogram index for the outgoing message length in units
		  of network cells."
	   ::= { lsEdgeSwToPortMsgLenEntry 2 }

         edgeToPortMsgLenMsgs OBJECT-TYPE
             SYNTAX  Counter
    	     ACCESS  read-only
             STATUS  mandatory
             DESCRIPTION
                 "Count of the number of outgoing messages of the given
                  length in terms of network cells."
	   ::= { lsEdgeSwToPortMsgLenEntry 3 }
 
 
-- Edge Processor(s) Workload Statistics

-- The structure of Edge workload statistics is to be defined.It will likely be
-- available only for low-speed cards (PP based instrumentation).
 
-- We provide a table with an uninterpreted variable type index
-- to specify the processor
-- and the workload variable of interest.  
-- It is assumed that utilization and other workload
-- statistics of interest can be derived from raw counters. 
--  For instance, if some counters
-- represent number of microseconds of work of the specified type,
-- interval utilization could
-- be derived directly from successive readings.
-- On the other hand, counts of fixed-cost
-- actions could be used to get a fix on overhead of the specified type,
--  particularly if
-- calibration data were available off-line.  
-- This is largely a 'PP' SW table, and
-- will likely not have an analog with the ASIC systems.

         lsEdgeCpuWorkloadTable OBJECT-TYPE
    	   SYNTAX  SEQUENCE OF LsEdgeCpuWorkloadEntry
           ACCESS  not-accessible
	   STATUS  mandatory
	   DESCRIPTION
               "Edge Card Workload Statistics Counter Table"
         ::= { lsEdgeStatistics	6 }

         lsEdgeCpuWorkloadEntry OBJECT-TYPE
	   SYNTAX   LsEdgeCpuWorkloadEntry
	   ACCESS   not-accessible
	   STATUS   mandatory
	   DESCRIPTION
	       "An entry in the Edge Cpu Workload Table"
	   INDEX   { lsEdgeWorkloadCardIndex,
			lsEdgeWorkloadTypeIndex }
	   ::= { lsEdgeCpuWorkloadTable 1 }

	 LsEdgeCpuWorkloadEntry ::=
	   SEQUENCE {
	       lsEdgeWorkloadCardIndex
	       	INTEGER,
	       lsEdgeWorkloadTypeIndex
	       	INTEGER,
	       lsEdgeWorkloadEvents
	       	Counter
	       }
         lsEdgeWorkloadCardIndex OBJECT-TYPE
             SYNTAX  INTEGER
    	     ACCESS  read-only
             STATUS  mandatory
             DESCRIPTION
                 "Unique Edge card Index consisting of slot number."
	   ::= { lsEdgeCpuWorkloadEntry 1 }
 
         lsEdgeWorkloadTypeIndex OBJECT-TYPE
             SYNTAX  INTEGER
    	     ACCESS  read-only
             STATUS  mandatory
             DESCRIPTION
                 "Index which identifies the Edge CPU Workload Variable"
	   ::= { lsEdgeCpuWorkloadEntry 2 }

         lsEdgeWorkloadEvents OBJECT-TYPE
             SYNTAX  Counter
    	     ACCESS  read-only
             STATUS  mandatory
             DESCRIPTION
                "Edge Cpu Workload Counter for the specified Workload Variable"
	   ::= { lsEdgeCpuWorkloadEntry 3 }


 -- FrameForward statistics specific to port

  lsFrameForwardStatTable OBJECT-TYPE
    SYNTAX  SEQUENCE OF LsFrameForwardStatEntry
    ACCESS  not-accessible
    STATUS  mandatory
    DESCRIPTION
        "FrameForward Port/ specific statistics subset information"
    ::= { lsEdgeStatistics 7 }

  lsFrameForwardStatEntry OBJECT-TYPE
    SYNTAX   LsFrameForwardStatEntry
    ACCESS   not-accessible
    STATUS   mandatory
    DESCRIPTION
        "An entry in the FrameForward Port/ Statistics Table."
    INDEX   { frameForwardStatPortIndex }
    ::= { lsFrameForwardStatTable 1 }

  LsFrameForwardStatEntry ::=
    SEQUENCE {
        frameForwardStatPortIndex
        	INTEGER,
        frameForwardToSwCLP0Frames
        	Counter,
        frameForwardToSwCLP0Cells
        	Counter,
        frameForwardToSwCLP1Frames
        	Counter,
        frameForwardToSwCLP1Cells
        	Counter,
        frameForwardToSwDiscardFrames
        	Counter,
        frameForwardToSwDiscardCells
        	Counter,
        frameForwardFrSwCLP0Frames
        	Counter,
        frameForwardFrSwCLP0Cells
        	Counter,
        frameForwardFrSwCLP1Frames
        	Counter,
        frameForwardFrSwCLP1Cells
        	Counter
        }

        	    
  frameForwardStatPortIndex OBJECT-TYPE
      SYNTAX  INTEGER
      ACCESS  read-only
      STATUS  mandatory
      DESCRIPTION
                  "This is the ifIndex value of the corresponding
		  ifEntry.  See comments above."
  ::= { lsFrameForwardStatEntry 1 }


  frameForwardToSwCLP0Frames OBJECT-TYPE
      SYNTAX  Counter
      ACCESS  read-only
      STATUS  mandatory
      DESCRIPTION
          "Number of Frames forwarded to TSU with CLP=0"
  ::= { lsFrameForwardStatEntry 2 }

  frameForwardToSwCLP0Cells OBJECT-TYPE
      SYNTAX  Counter
      ACCESS  read-only
      STATUS  mandatory
      DESCRIPTION
          "Number of Cells forwarded to TSU with CLP=0"
  ::= { lsFrameForwardStatEntry 3 }


  frameForwardToSwCLP1Frames OBJECT-TYPE
      SYNTAX  Counter
      ACCESS  read-only
      STATUS  mandatory
      DESCRIPTION
          "Number of Frames forwarded to TSU with CLP=1"
  ::= { lsFrameForwardStatEntry 4 }

  frameForwardToSwCLP1Cells OBJECT-TYPE
      SYNTAX  Counter
      ACCESS  read-only
      STATUS  mandatory
      DESCRIPTION
          "Number of Cells forwarded to TSU with CLP=1"
  ::= { lsFrameForwardStatEntry 5 }

  frameForwardToSwDiscardFrames OBJECT-TYPE
      SYNTAX  Counter
      ACCESS  read-only
      STATUS  mandatory
      DESCRIPTION
          "Number of to-switch Frames discarded due to excessive traffic
 	  according to the Usage Parameter Descriptor for this "
  ::= { lsFrameForwardStatEntry 6 }

  frameForwardToSwDiscardCells OBJECT-TYPE
      SYNTAX  Counter
      ACCESS  read-only
      STATUS  mandatory
      DESCRIPTION
          "Number of to-switch Cells discarded due to excessive traffic
 	  according to the Usage Parameter Descriptor for this "
  ::= { lsFrameForwardStatEntry 7 }

  frameForwardFrSwCLP0Frames OBJECT-TYPE
      SYNTAX  Counter
      ACCESS  read-only
      STATUS  mandatory
      DESCRIPTION
          "Number of frames received from the switch with CLP=0"
  ::= { lsFrameForwardStatEntry 8 }

  frameForwardFrSwCLP0Cells OBJECT-TYPE
      SYNTAX  Counter
      ACCESS  read-only
      STATUS  mandatory
      DESCRIPTION
          "Number of cells received from the switch with CLP=0"
  ::= { lsFrameForwardStatEntry 9 }


  frameForwardFrSwCLP1Frames OBJECT-TYPE
      SYNTAX  Counter
      ACCESS  read-only
      STATUS  mandatory
      DESCRIPTION
          "Number of frames received from the switch with CLP=1"
  ::= { lsFrameForwardStatEntry 10 }

  frameForwardFrSwCLP1Cells OBJECT-TYPE
      SYNTAX  Counter
      ACCESS  read-only
      STATUS  mandatory
      DESCRIPTION
          "Number of cells received from the switch with CLP=1"
  ::= { lsFrameForwardStatEntry 11 }



 
--	TRUNK STATISTICS SUBSET
 
	 lsTrunkStatistics OBJECT IDENTIFIER ::= { lsExperimentalStatistics 2 }

	-- Statistics associated with each Trunk Port, including the CP port
         lsTrunkPortStatTable OBJECT-TYPE
    	   SYNTAX  SEQUENCE OF LsTrunkPortStatEntry
           ACCESS  not-accessible
	   STATUS  mandatory
	   DESCRIPTION
               "Trunk Card specific statistics subset information"
	   ::= { lsTrunkStatistics 1 }

	 lsTrunkPortStatEntry OBJECT-TYPE
	   SYNTAX   LsTrunkPortStatEntry
	   ACCESS   not-accessible
	   STATUS   mandatory
	   DESCRIPTION
	       "An entry in Trunk Port Statistics Table."
	   INDEX   { trunkPortStatIndex }
	   ::= { lsTrunkPortStatTable 1 }

	 LsTrunkPortStatEntry ::=
	   SEQUENCE {
	       trunkPortStatIndex
	       	INTEGER,
	       trunkPortRcvCells
	       	Counter,
	       trunkPortXmtCells
	       	Counter,
	       trunkPortRcvRuns
	       	Counter,
	       trunkPortDownXmtCells
	       	Counter,
 
	-- The following are essentially L2 errors and may need
        -- to go somewhere else or may not be used.  These errors derive from
        -- I/O hardware, and may duplicate information in another portion
		-- of the atmSwitch MIB.  Likely to be incomplete.
	       trunkPortRcvCRCErrors
	       	Counter,
	       trunkPortRcvAborts
	       	Counter,
	       trunkPortXmtUnderflows
	       	Counter,
	       trunkPortRcvShortFrames
	       	Counter
	       }
    	       	    
         trunkPortStatIndex OBJECT-TYPE
             SYNTAX  INTEGER
    	     ACCESS  read-only
             STATUS  mandatory
             DESCRIPTION
                  "This is the ifIndex value of the corresponding
		  ifEntry.  See comments above."
         ::= { lsTrunkPortStatEntry 1 }

  -- The following operational statistics are reported on a per-port basis.
         trunkPortRcvCells OBJECT-TYPE
             SYNTAX  Counter
    	     ACCESS  read-only
             STATUS  mandatory
             DESCRIPTION
                 "Number of cells received regardless of error status"
         ::= { lsTrunkPortStatEntry 2 }

         trunkPortXmtCells OBJECT-TYPE
             SYNTAX  Counter
    	     ACCESS  read-only
             STATUS  mandatory
             DESCRIPTION
                 "Number of cells transmitted regardless of error status"
         ::= { lsTrunkPortStatEntry 3 }

 
	-- The Run counter may not be implemented for some or all cards.
	-- If unimplemented on all cards, this object will be eliminated.  If
        -- unimplemented on only some cards, will return a zero value when
        -- not implemented.
         trunkPortRcvRuns OBJECT-TYPE
             SYNTAX  Counter
    	     ACCESS  read-only
             STATUS  mandatory
             DESCRIPTION
                 "The number of runs of cells received.  A Run is a sequence of
                  Non-Null Cells bounded by Null Cells."
         ::= { lsTrunkPortStatEntry 4 }

         trunkPortDownXmtCells OBJECT-TYPE
             SYNTAX  Counter
    	     ACCESS  read-only
             STATUS  mandatory
             DESCRIPTION
                 "The number of cells received by the TSU for which the
                  the VCI was not configured."
         ::= { lsTrunkPortStatEntry 5 }

 
	-- Begin L2 error Definitions.  May want to put elsewhere or in
	-- separate table.
         trunkPortRcvCRCErrors OBJECT-TYPE
             SYNTAX  Counter
    	     ACCESS  read-only
             STATUS  mandatory
             DESCRIPTION
                 "The number of messages received by the port with CRC errors."
         ::= { lsTrunkPortStatEntry 6 }
 
         trunkPortRcvAborts OBJECT-TYPE
             SYNTAX  Counter
    	     ACCESS  read-only
             STATUS  mandatory
             DESCRIPTION
                 "The number of aborts detected by the HW."
         ::= { lsTrunkPortStatEntry 7 }

         trunkPortXmtUnderflows OBJECT-TYPE
             SYNTAX  Counter
    	     ACCESS  read-only
             STATUS  mandatory
             DESCRIPTION
                 "The number of underflow events detected by I/O hardware."
         ::= { lsTrunkPortStatEntry 8 }

 
         trunkPortRcvShortFrames OBJECT-TYPE
             SYNTAX  Counter
    	     ACCESS  read-only
             STATUS  mandatory
             DESCRIPTION
                 "The number of short incoming frames detected by L2"
         ::= { lsTrunkPortStatEntry 9 }

 
-- Trunk Processor(s) Workload Statistics

-- The structure of Trunk workload statistics is to be defined.  
-- It will likely be
-- available only for low-speed cards (PP based instrumentation).
 
-- We provide a table with an uninterpreted variable type 
-- index to specify the processor
-- and the workload variable of interest.
-- It is assumed that utilization and other work
-- statistics of interest can be derived from raw counters.
-- For instance, if some counters
-- represent number of microseconds of work of the specified type, 
-- interval utilization could
-- be derived directly from successive readings.  
-- On the other hand, counts of fixed-cost
-- actions could be used to get a fix on overhead of the 
-- specified type, particularly if
-- calibration data were available off-line.
 
-- NOTE:  While this table looks like the same one used for the edge cards,
--           these two systems may have different types of workload indicators.
--           Should some kind of common definition be used?

         lsTrunkCpuWorkloadTable OBJECT-TYPE
    	   SYNTAX  SEQUENCE OF LsTrunkCpuWorkloadEntry
           ACCESS  not-accessible
	   STATUS  mandatory
	   DESCRIPTION
               "Trunk Card Workload Statistics Counter Table"
         ::= { lsTrunkStatistics	2 }

         lsTrunkCpuWorkloadEntry OBJECT-TYPE
	   SYNTAX   LsTrunkCpuWorkloadEntry
	   ACCESS   not-accessible
	   STATUS   mandatory
	   DESCRIPTION
	       "An entry in the Trunk Cpu Workload Table"
	   INDEX   { lsTrunkWorkloadCardIndex,
			lsTrunkWorkloadTypeIndex }
	   ::= { lsTrunkCpuWorkloadTable 1 }

	 LsTrunkCpuWorkloadEntry ::=
	   SEQUENCE {
	       lsTrunkWorkloadCardIndex
	       	INTEGER,
	       lsTrunkWorkloadTypeIndex
	       	INTEGER,
	       lsTrunkWorkloadEvents
	       	Counter
	       }
 
         lsTrunkWorkloadCardIndex OBJECT-TYPE
             SYNTAX  INTEGER
    	     ACCESS  read-only
             STATUS  mandatory
             DESCRIPTION
                 "Unique Trunk card Index consisting of card's slot number"
	   ::= { lsTrunkCpuWorkloadEntry 1 }
 

         lsTrunkWorkloadTypeIndex OBJECT-TYPE
             SYNTAX  INTEGER  {
				average (1)
		   		}

    	     ACCESS  read-only
             STATUS  mandatory
             DESCRIPTION
                 "Trunk CPU Workload Counter Variable:
                     1 - average workload"
	   ::= { lsTrunkCpuWorkloadEntry 2 }

         lsTrunkWorkloadEvents OBJECT-TYPE
             SYNTAX  Counter
    	     ACCESS  read-only
             STATUS  mandatory
             DESCRIPTION
               "Trunk Cpu Workload Counter for the specified Workload Variable"
	   ::= { lsTrunkCpuWorkloadEntry 3 }
 
 
 --    Line Card Common Branch.
 --    This branch avoids duplication of tables for Trunk and Edge cards
        -- Common FSU statistics
        -- Common TSU statistics

	 lsLcStatistics OBJECT IDENTIFIER ::= { lsExperimentalStatistics 3 }
 
         -- FSU and TSU Stat Objects indexed by LC card alone
         lcStatTable OBJECT-TYPE
    	   SYNTAX  SEQUENCE OF LcStatEntry
           ACCESS  not-accessible
	   STATUS  mandatory
	   DESCRIPTION
             "Table of objects, such as FSU and TSU objects, which exist across
              for either trunk or edge cards, indexed by the line card alone.
              Some of these objects may require ASIC HW."
         ::= { lsLcStatistics	1 }

         lcStatEntry OBJECT-TYPE
	   SYNTAX   LcStatEntry
	   ACCESS   not-accessible
	   STATUS   mandatory
	   DESCRIPTION
	       "An entry in the LC common FSU Stat table."
	   INDEX   { lcStatCardIndex }
	   ::= { lcStatTable 1 }

	 LcStatEntry ::=
	   SEQUENCE {
               lcStatCardIndex
	       	INTEGER,
	       tsuFreeCells
	       	Gauge,
               fsuSharedFreeCells
	       	INTEGER,
               tsuCellDropLastVci
                INTEGER,
               switchCellDgRejectEvents
                Counter,
               switchCellSchedRejectEvents
                Counter,
	       tsuErrFutQCellDrops
	       	Counter,
	       tsuErrFutQMsgDropLastVci
	       	INTEGER,
	       fsuHdrLrcErrs
	       	Counter,
	       fsuPayloadLrcErrs
	       	Counter
	       }
 
         lcStatCardIndex OBJECT-TYPE
             SYNTAX  INTEGER
    	     ACCESS  read-only
             STATUS  mandatory
             DESCRIPTION
                 "Unique Line Card index"
	   ::= { lcStatEntry 1 }

         tsuFreeCells OBJECT-TYPE
             SYNTAX  Gauge
    	     ACCESS  read-only
             STATUS  mandatory
             DESCRIPTION
                 "The total number of free cells available on the Tsu"
         ::= { lcStatEntry 2 }

         fsuSharedFreeCells OBJECT-TYPE
             SYNTAX  INTEGER
    	     ACCESS  read-only
             STATUS  mandatory
             DESCRIPTION
                 "Number of Cells on the shared free-list in the FSU."
	   ::= { lcStatEntry 3 }

 
         tsuCellDropLastVci OBJECT-TYPE
             SYNTAX  INTEGER
    	     ACCESS  read-only
             STATUS  mandatory
             DESCRIPTION
                 "The last VCI index associated with a message dropped by the
                  TSU due to buffer shortage.  This index implicitly determines
                  the port and connection."
	   ::= { lcStatEntry 4 }

             switchCellDgRejectEvents OBJECT-TYPE
             SYNTAX  Counter
    	     ACCESS  read-only
             STATUS  mandatory
             DESCRIPTION
             "The number of switch rejects of datagram cells.  These are
              not errors, but this does provide a measure of switch contention.
              May only be available on ASIC HW Line Cards."
	   ::= { lcStatEntry 5 }
 
             switchCellSchedRejectEvents OBJECT-TYPE
             SYNTAX  Counter
    	     ACCESS  read-only
             STATUS  mandatory
             DESCRIPTION
                 "The number of switch rejects of datagram cells.  These are
                  errors, since appropriate scheduling should not allow these.
                  May only be available on ASIC HW Line Cards."
	   ::= { lcStatEntry 6 }
 
         tsuErrFutQCellDrops OBJECT-TYPE
             SYNTAX  Counter
    	     ACCESS  read-only
             STATUS  mandatory
             DESCRIPTION
                 "The number of cells dropped due to FutureQ Overruns"
         ::= { lcStatEntry 7 }

         tsuErrFutQMsgDropLastVci OBJECT-TYPE
             SYNTAX  INTEGER
    	     ACCESS  read-only
             STATUS  mandatory
             DESCRIPTION
                 "The last Vci index associated with a cell dropped due to
                  FutureQ overrun."
         ::= { lcStatEntry 8 }

         fsuHdrLrcErrs OBJECT-TYPE
             SYNTAX  Counter
    	     ACCESS  read-only
             STATUS  mandatory
             DESCRIPTION
                 "The total number of LRC errors detected by the FSU"
         ::= { lcStatEntry 9 }

         fsuPayloadLrcErrs OBJECT-TYPE
             SYNTAX  Counter
    	     ACCESS  read-only
             STATUS  mandatory
             DESCRIPTION
                 "The total number of LRC errors detected by the FSU"
         ::= { lcStatEntry 10 }

 
         -- LC Statistics common to Edge and Trunk line-cards, indexed by Port
 
         lcPortStatTable OBJECT-TYPE
    	   SYNTAX  SEQUENCE OF LcPortStatEntry
           ACCESS  not-accessible
	   STATUS  mandatory
	   DESCRIPTION
          "Table of Line Card (Edge and Trunk) Statistics by port.  There are
           a number of TSU and FSU statistics in common to edges and trunks.
           Some of the objects in this table may be limited in use to ASIC HW."
         ::= { lsLcStatistics	2 }

         lcPortStatEntry OBJECT-TYPE
	   SYNTAX   LcPortStatEntry
	   ACCESS   not-accessible
	   STATUS   mandatory
	   DESCRIPTION
	       "An entry in the Line Card Stat Table, indexed by port."
	   INDEX   { lcStatPortIndex }
	   ::= { lcPortStatTable 1 }

	 LcPortStatEntry ::=
	   SEQUENCE {
	       lcStatPortIndex
	       	INTEGER,
               fsuPortFreeCells
                Gauge,
	       fsuCellDropLastCellHdr
	       	INTEGER,
               tsuPortErrL1UnconfigVcis
                Counter,
               tsuPortErrL2UnconfigVcis
                Counter,
               tsuPortErrL1UnconfigLastVci
                INTEGER,
               tsuPortErrL2UnconfigLastVci
                INTEGER,
               tsuPortErrNonZeroGfc
                Counter
	       }
 
         lcStatPortIndex OBJECT-TYPE
             SYNTAX  INTEGER
    	     ACCESS  read-only
             STATUS  mandatory
             DESCRIPTION
                  "This is the ifIndex value of the corresponding
		  ifEntry.  See comments above."
	   ::= { lcPortStatEntry 1 }

         fsuPortFreeCells OBJECT-TYPE
             SYNTAX  Gauge
    	     ACCESS  read-only
             STATUS  mandatory
             DESCRIPTION
                 "Number of Cells on per-port FSU free lists."
	   ::= { lcPortStatEntry 2 }

         fsuCellDropLastCellHdr OBJECT-TYPE
             SYNTAX  INTEGER
    	     ACCESS  read-only
             STATUS  mandatory
             DESCRIPTION
            "The last Cell Header associated with a FSU cell drop due to buffer
            shortage.  Provides a clue as to which VCIs are being dropped.
            Since this is a full 32-bit header, the CLP bit state is available.
            The XCLP and Queue can be inferred from indirect lookup based
            on the header, if desired."
	   ::= { lcPortStatEntry 3 }

         tsuPortErrL1UnconfigVcis OBJECT-TYPE
             SYNTAX  Counter
    	     ACCESS  read-only
             STATUS  mandatory
             DESCRIPTION
                 "The number of cells received by the TSU for which the
                  the VCI was not configured within the Level 1 table.
                  Cells for unconfigured VCIs are dropped."
         ::= { lcPortStatEntry 4 }

         tsuPortErrL2UnconfigVcis OBJECT-TYPE
             SYNTAX  Counter
    	     ACCESS  read-only
             STATUS  mandatory
             DESCRIPTION
                 "The number of cells received by the TSU for which the
                  the VCI was not configured within the Level 2 table.
                  Cells for unconfigured VCIs are dropped."
         ::= { lcPortStatEntry 5 }

         tsuPortErrL1UnconfigLastVci OBJECT-TYPE
             SYNTAX  INTEGER
    	     ACCESS  read-only
             STATUS  mandatory
             DESCRIPTION
                 "The last 4-byte cell header associated with a Level 1
                  unconfigured VCI."
         ::= { lcPortStatEntry 6 }

         tsuPortErrL2UnconfigLastVci OBJECT-TYPE
             SYNTAX  INTEGER
    	     ACCESS  read-only
             STATUS  mandatory
             DESCRIPTION
                 "The last 4-byte cell header associated with a Level 2
                  unconfigured VCI."
         ::= { lcPortStatEntry 7 }

         tsuPortErrNonZeroGfc OBJECT-TYPE
             SYNTAX  Counter
    	     ACCESS  read-only
             STATUS  mandatory
             DESCRIPTION
                 "For a UNI, the number of cells received with a non-zero
                  GFC byte.  No action taken aside from counting."
         ::= { lcPortStatEntry 8 }

 
         -- Table of FSU cells transmitted indexed by port and drop priority.
         fsuPortXmtCellsTable OBJECT-TYPE
    	   SYNTAX  SEQUENCE OF FsuPortXmtCellsEntry
           ACCESS  not-accessible
	   STATUS  mandatory
	   DESCRIPTION
           "Table of cells transmited by FSU to either a line-card
	   chip or TLU, indexed by port and a drop priority subindex
	   which represents the CLP and XCLP status of the cells.  The
	   priority index is tentatively defined as 2*CLP + XCLP + 1.
	   Does not count cells dropped due to FSU buffer shortages or
	   header LRC errors. 
 
           Availability may depend on HW."
         ::= { lsLcStatistics	3 }

         fsuPortXmtCellsEntry OBJECT-TYPE
	   SYNTAX   FsuPortXmtCellsEntry
	   ACCESS   not-accessible
	   STATUS   mandatory
	   DESCRIPTION
	       "An entry in the LC common FSU Port Xmt Cells Table."
	   INDEX   { fsuXmtCellsPortIndex,
                        fsuXmtCellsPriorityIndex }
	   ::= { fsuPortXmtCellsTable 1 }

	 FsuPortXmtCellsEntry ::=
	   SEQUENCE {
               fsuXmtCellsPortIndex
	       	INTEGER,
               fsuXmtCellsPriorityIndex
	       	INTEGER,
	       fsuXmtCellEvents
	       	Counter
	       }
 
         fsuXmtCellsPortIndex OBJECT-TYPE
             SYNTAX  INTEGER
    	     ACCESS  read-only
             STATUS  mandatory
             DESCRIPTION
                  "This is the ifIndex value of the corresponding
		  ifEntry.  See comments above."
	   ::= { fsuPortXmtCellsEntry 1 }

         fsuXmtCellsPriorityIndex OBJECT-TYPE
             SYNTAX  INTEGER (1..4)
    	     ACCESS  read-only
             STATUS  mandatory
             DESCRIPTION
                 "Index specifying the CLP and XCLP priority substream
                  for the port.  Index defined as 2*CLP + XCLP + 1."
	   ::= { fsuPortXmtCellsEntry 2 }

         fsuXmtCellEvents OBJECT-TYPE
             SYNTAX  Counter
    	     ACCESS  read-only
             STATUS  mandatory
             DESCRIPTION
                 "Number of cells forwarded by the FSU towards the port
                  indicated by the PortIndex, by the specified priority."
	   ::= { fsuPortXmtCellsEntry 3 }

-- FSU Queue size statistics.  The queue size is in terms of cells.  Doubly
-- indexed by Port and SubQueue within port.  This indexing avoids the problem
-- of wiring in the number of subqueues per port.
 

         fsuQueueCellLengthTable OBJECT-TYPE
    	   SYNTAX  SEQUENCE OF FsuQueueCellLenEntry
           ACCESS  not-accessible
	   STATUS  mandatory
	   DESCRIPTION
               "Table of current queue lengths by port and subqueue as
                measured in cells."
         ::= { lsLcStatistics	4}

         fsuQueueCellLenEntry OBJECT-TYPE
	   SYNTAX   FsuQueueCellLenEntry
	   ACCESS   not-accessible
	   STATUS   mandatory
	   DESCRIPTION
	       "An entry in the FSU queue length table"
	   INDEX   { fsuQueueCellLenPortIndex,
                        fsuQueueCellLenSubQIndex }
	   ::= { fsuQueueCellLengthTable 1 }

	 FsuQueueCellLenEntry ::=
	   SEQUENCE {
	       fsuQueueCellLenPortIndex
	       	INTEGER,
	       fsuQueueCellLenSubQIndex
	       	INTEGER,
	       fsuQueueCellLength
	       	Gauge
	       }
 
 
         fsuQueueCellLenPortIndex OBJECT-TYPE
             SYNTAX  INTEGER
    	     ACCESS  read-only
             STATUS  mandatory
             DESCRIPTION
                  "This is the ifIndex value of the corresponding
		  ifEntry.  See comments above."
	   ::= { fsuQueueCellLenEntry 1 }

         fsuQueueCellLenSubQIndex OBJECT-TYPE
             SYNTAX  INTEGER (1..5)
    	     ACCESS  read-only
             STATUS  mandatory
             DESCRIPTION
                 "Index specifying the subqueue for the port, where
		  a lower queue number has a lower fsu priority."
	   ::= { fsuQueueCellLenEntry 2 }

 
         fsuQueueCellLength OBJECT-TYPE
             SYNTAX  Gauge
    	     ACCESS  read-only
             STATUS  mandatory
             DESCRIPTION
                 "Length of the specified queue in cell units.  For ASIC Edge versions,
                  this will include cells on the reassembly Queue for a port.  For
                  non-ASIC Edge versions, does not include reassembly Queue.  Non-ASIC
                  versions provide an estimate due to slow-side scanner logic, while
                  ASIC versions provide direct counts."
	   ::= { fsuQueueCellLenEntry 3 }

-- FSU Port-specific Drop Statistics, maintained essentially
-- by Qbyte (queue and drop priority CLP/XCLP).  We provide a port index and
-- a single consolodated "watermark index", where the latter may undergo redefinition
-- depending on the HW.  There may be some need to provide an additional table
-- for mapping Queue/XCLP/CLP into the appropriate watermark index.
 
--  Note that for the ASIC these are cell, not message drop statistics.  It is possible
--  that the non-ASIC version will count message drops instead of cells (due to the
--  slow scan logic).  In order to maintain one table, we use drop "Events".
--
-- A separate per-port table (without a subindex) is used to keep trac<k of the last
-- cell header (32 bit) associated with a drop so we can see if there is some consistency.
 
         fsuDropEventTable OBJECT-TYPE
    	   SYNTAX  SEQUENCE OF FsuDropEventEntry
           ACCESS  not-accessible
	   STATUS  mandatory
	   DESCRIPTION
               "Table of drop events by FSU due to buffer shortage,
                by Port and drop watermark.  This table may be limited
                in use to ASIC HW.  For ASIC these are cell drops.  For
                non-ASIC, might be messages instead of cells."
         ::= { lsLcStatistics	5 }

         fsuDropEventEntry OBJECT-TYPE
	   SYNTAX   FsuDropEventEntry
	   ACCESS   not-accessible
	   STATUS   mandatory
	   DESCRIPTION
	       "An entry in the FSU Port/Watermark drop event table"
	   INDEX   { fsuDropEventPortIndex,
                        fsuDropEventWatermarkIndex }
	   ::= { fsuDropEventTable 1 }

	 FsuDropEventEntry ::=
	   SEQUENCE {
	       fsuDropEventPortIndex
	       	INTEGER,
	       fsuDropEventWatermarkIndex
	       	INTEGER,
	       fsuDropEvents
	       	Counter
	       }
 
         fsuDropEventPortIndex OBJECT-TYPE
             SYNTAX  INTEGER
    	     ACCESS  read-only
             STATUS  mandatory
             DESCRIPTION
                  "This is the ifIndex value of the corresponding
		  ifEntry.  See comments above."
	   ::= { fsuDropEventEntry 1 }

         fsuDropEventWatermarkIndex OBJECT-TYPE
             SYNTAX  INTEGER
    	     ACCESS  read-only
             STATUS  mandatory
             DESCRIPTION
       "Watermark associated with the drop count.  The watermark
        selected is a function of the Fsu Priority, CLP and XCLP within
	port.  We tentively define it to be (FSU-Priority)*4 + 2*CLP + XCLP+1.
        CLP and XCLP are 0/1 valued.  At this time, there are eight Fsu
        priorities (treated as 0-7 in increasing priority), however these
        components cannot vary independently as currently used.  Therefore,
        some entries will either not exist or will have a non-varying (default)
        count of zero."
	   ::= { fsuDropEventEntry 2 }

         fsuDropEvents OBJECT-TYPE
             SYNTAX  Counter
    	     ACCESS  read-only
             STATUS  mandatory
             DESCRIPTION
                 "Count of the number drop events (cells or messages) dropped by
		  the FSU due to low buffers, for the specified port and
	          drop watermark."
	   ::= { fsuDropEventEntry 3 }

 
--  FSU Fast (cell) Drop Statistics are maintained essentially indexed by
-- a watermark index.  This corresponds to "fast-side" drops for those non-ASIC
-- cards which have a global, simplistic fast drop mechanism (this uses
-- only CLP/XCLP cell status and buffer pool size to make
-- drop decision with three watermarks and three counters).
 
-- Other cards may have a more refined cell drop mechanisms.
-- which utilizes a full set of watermarks to drop cells (see fsuDropEventTable).
 
         lsFsuFastDropTable OBJECT-TYPE
    	   SYNTAX  SEQUENCE OF LsFsuFastDropEntry
           ACCESS  not-accessible
	   STATUS  mandatory
	   DESCRIPTION
               "Table of cells dropped by FSU due to buffer shortage,
                by drop watermark, for cards using the fast-side drop
                mechanism.  These statistics are not available for other cards."
         ::= { lsLcStatistics	6 }

         lsFsuFastDropEntry OBJECT-TYPE
	   SYNTAX   LsFsuFastDropEntry
	   ACCESS   not-accessible
	   STATUS   mandatory
	   DESCRIPTION
	       "An entry in the FSU fast-side per watermark drop table"
	   INDEX   { lsFsuFastDropWatermarkIndex }
	   ::= { lsFsuFastDropTable 1 }

	 LsFsuFastDropEntry ::=
	   SEQUENCE {
	       lsFsuFastDropWatermarkIndex
	       	INTEGER,
	       lsFsuFastCellDropEvents
	       	Counter
	       }
 
	-- There are currently three counters for the non-ASIC
	-- cards.  May need adjustment.
         lsFsuFastDropWatermarkIndex OBJECT-TYPE
             SYNTAX  INTEGER {
			clp1(1),
			clp0HiPriority(2),
			clp0HiOther(3)
			}
    	     ACCESS  read-only
             STATUS  mandatory
             DESCRIPTION
                 "Watermark used for dropping with the fast-drop mechanism."
	   ::= { lsFsuFastDropEntry 1 }

         lsFsuFastCellDropEvents OBJECT-TYPE
             SYNTAX  Counter
    	     ACCESS  read-only
             STATUS  mandatory
             DESCRIPTION
                 "Count of the number cells dropped by FSU due
		  to low buffers, for the specified watermark, using the
                  fast-drop mechanism.  These should be rare if the
                  slow-side mechanism is functioning properly."
	   ::= { lsFsuFastDropEntry 2 }

 
-- TSU Objects common to Edge and Trunk cards

-- TSU WaterMark drop Statistics are doubly indexed (by port and watermark).
-- Although there are only two watermarks defined now (CNTL == DG3 and Other),
-- we explicitly provide a watermark to permit future expansion.
-- TSU Watermark drops occur only due to buffer shortage.  The two watermarks
-- are intended to insure that control traffic can be accepted.
 
        tsuDropEventTable OBJECT-TYPE
    	   SYNTAX  SEQUENCE OF TsuDropEventEntry
           ACCESS  not-accessible
	   STATUS  mandatory
	   DESCRIPTION
               "Table of drop events by TSU due to buffer shortage,
                by Port and drop watermark.  A drop event corresponds to
                a cell drop for ASIC cards.  It may correspond to frame drops`
                on other cards."
         ::= { lsLcStatistics	7 }

         tsuDropEventEntry OBJECT-TYPE
	   SYNTAX   TsuDropEventEntry
	   ACCESS   not-accessible
	   STATUS   mandatory
	   DESCRIPTION
	       "An entry in the Edge Port/Watermark TSU drop events table"
	   INDEX   { tsuDropEventPortIndex,
                        tsuDropEventWatermarkIndex }
	   ::= { tsuDropEventTable 1 }

	 TsuDropEventEntry ::=
	   SEQUENCE {
	       tsuDropEventPortIndex
	       	INTEGER,
	       tsuDropEventWatermarkIndex
	       	INTEGER,
	       tsuDropEvents
	       	Counter
	       }
 
         tsuDropEventPortIndex OBJECT-TYPE
             SYNTAX  INTEGER
    	     ACCESS  read-only
             STATUS  mandatory
             DESCRIPTION
                  "This is the ifIndex value of the corresponding
		  ifEntry.  See comments above."
	   ::= { tsuDropEventEntry 1 }

         tsuDropEventWatermarkIndex OBJECT-TYPE
             SYNTAX  INTEGER {
				user      (1),
				control   (2),
				scheduled (3)
		   		}
    	     ACCESS  read-only
             STATUS  mandatory
             DESCRIPTION
                 "Watermark associated with the drop count."
	   ::= { tsuDropEventEntry 2 }

         tsuDropEvents OBJECT-TYPE
             SYNTAX  Counter
    	     ACCESS  read-only
             STATUS  mandatory
             DESCRIPTION
                 "TSU drop events due to low buffers,
                  for the specified port and drop watermark.
 
                  For ASIC cards these are cell drops.  For other cards
                  the unit may be messages, depending on the card.  These
                  drops should be rare.  They could be a byproduct of incorrect
                  scheduled service setup."
	   ::= { tsuDropEventEntry 3 }

 
--	UTILIZATION SUBSET Historical Info.  THIS SUBTREE IS PRELIMINARY.
 
	lsUtStatistics OBJECT IDENTIFIER ::= { lsExperimentalStatistics 4}
 
-- Outbound Line card (FSU) queue statistics.  The primary information
-- of interest relates to sampled queue depth and total discards.  Discard details
-- can be obtained from the standard table.
 
	lsLcFsuIntervalTable OBJECT-TYPE
    	   SYNTAX  SEQUENCE OF LsLcFsuIntervalEntry
           ACCESS  not-accessible
	   STATUS  mandatory
	   DESCRIPTION
               "Table of sampled FSU queue depths and drop information,
		by outbound port (trunk and edge) where sampling occurs
		for queue depth is sampled once per second and data is
		aggregated into one minute buckets defined by the
		lsLcIntervalNumber."
         ::= { lsUtStatistics	1 }
 

	lsLcFsuIntervalEntry OBJECT-TYPE
	   SYNTAX   LsLcFsuIntervalEntry
	   ACCESS   not-accessible
	   STATUS   mandatory
	   DESCRIPTION
	       "An entry in the LC FSU Interval table"
	   INDEX   { lsLcIntervalPortIndex,
                     --   lsLcIntervalSubQIndex,
			lsLcIntervalNumber }
	   ::= { lsLcFsuIntervalTable 1 }

	 LsLcFsuIntervalEntry ::=
	   SEQUENCE {
	       lsLcIntervalPortIndex
	       	INTEGER,
	       lsLcIntervalNumber
		INTEGER (1..60),
	       lsLcIntervalPSDepth
	       	INTEGER,
	       lsLcIntervalASDepth
		INTEGER,
	       lsLcIntervalDropEvents
		INTEGER,
	       lsLcIntervalAvgCells
		INTEGER,
	       lsLcIntervalPeakCells
		INTEGER,
	       lsLcIntervalMinPermits
		INTEGER,
	       lsLcIntervalAvgPermits
		INTEGER,
	       lsLcIntervalMaxPermits
		INTEGER,
	       lsLcIntervalDecrPermits
		INTEGER,
	       lsLcIntervalIncrPermits
		INTEGER,
	       lsLcIntervalMinBwAlloc
		INTEGER,
	       lsLcIntervalAvgBwAlloc
		INTEGER,
	       lsLcIntervalMaxBwAlloc
		INTEGER
	       }
 
         lsLcIntervalPortIndex OBJECT-TYPE
             SYNTAX  INTEGER
    	     ACCESS  read-only
             STATUS  mandatory
             DESCRIPTION
                  "This is the ifIndex value of the corresponding
		  ifEntry.  See comments above.

		  The port may be logical (e.g. terminated by a processor)."
	   ::= {lsLcFsuIntervalEntry 1 }

 
         lsLcIntervalNumber OBJECT-TYPE
             SYNTAX  INTEGER (1..60)
    	     ACCESS  read-only
             STATUS  mandatory
             DESCRIPTION
                 "A number between 1 and 60, where 1 is the most
		  recently completed 1 minute interval and 60 is the
                  least recently completed one minute interval
                  (assuming that all 60 intervals are valid).
                  Currently only interval of 1 is supported"
	   ::= {lsLcFsuIntervalEntry 2 }

         lsLcIntervalPSDepth OBJECT-TYPE
             SYNTAX  INTEGER
    	     ACCESS  read-only
             STATUS  mandatory
             DESCRIPTION
                 "Peak sampled queue depth for this outbound port,
                  in cells, where queue depth is sampled once per second."
	   ::= {lsLcFsuIntervalEntry 3 }
 
         lsLcIntervalASDepth OBJECT-TYPE
             SYNTAX  INTEGER
    	     ACCESS  read-only
             STATUS  mandatory
             DESCRIPTION
                 "Average sampled queue depth for this outbound port,
                  in cells, where queue depth is sampled once per second."
	   ::= {lsLcFsuIntervalEntry 4 }
 
         lsLcIntervalDropEvents OBJECT-TYPE
             SYNTAX  INTEGER
    	     ACCESS  read-only
             STATUS  mandatory
             DESCRIPTION
                 "The Number of cell drop events encountered for
                  this port during the specified interval.  This provides
		  the average cell loss ratio over the interval."
	   ::= {lsLcFsuIntervalEntry 5 }
 
         lsLcIntervalAvgCells OBJECT-TYPE
             SYNTAX  INTEGER
    	     ACCESS  read-only
             STATUS  mandatory
             DESCRIPTION
                 "The Number of cells transmitted for
                  this port during the specified interval.
		  This provides average utilization over the interval."
	   ::= {lsLcFsuIntervalEntry 6 }
 
         lsLcIntervalPeakCells OBJECT-TYPE
             SYNTAX  INTEGER
    	     ACCESS  read-only
             STATUS  mandatory
             DESCRIPTION
                 "The Peak Number of cells transmitted for this port
		  during any one second measurement period within the
		  specified interval. This provides peak one-second
		  utilization information."
	   ::= {lsLcFsuIntervalEntry 7 }
 
         lsLcIntervalMinPermits OBJECT-TYPE
             SYNTAX  INTEGER
    	     ACCESS  read-only
             STATUS  mandatory
             DESCRIPTION
                 "The Minimum Permit value as sampled once per second
		  during the specified interval."
	   ::= {lsLcFsuIntervalEntry 8 }
 
         lsLcIntervalAvgPermits OBJECT-TYPE
             SYNTAX  INTEGER
    	     ACCESS  read-only
             STATUS  mandatory
             DESCRIPTION
                 "The Average Permit value as sampled once per second
		  during the specified interval."
	   ::= {lsLcFsuIntervalEntry 9 }
 
         lsLcIntervalMaxPermits OBJECT-TYPE
             SYNTAX  INTEGER
    	     ACCESS  read-only
             STATUS  mandatory
             DESCRIPTION
                 "The Maximum Permit value as sampled once per second
		  during the specified interval."
	   ::= {lsLcFsuIntervalEntry 10 }
 
         lsLcIntervalDecrPermits OBJECT-TYPE
             SYNTAX  INTEGER
    	     ACCESS  read-only
             STATUS  mandatory
             DESCRIPTION
                 "The Number of Permit decrease updates
		  submitted during the current interval"
	   ::= {lsLcFsuIntervalEntry 11 }
 
         lsLcIntervalIncrPermits OBJECT-TYPE
             SYNTAX  INTEGER
    	     ACCESS  read-only
             STATUS  mandatory
             DESCRIPTION
                 "The Number of Permit increase updates
		  submitted during the current interval"
	   ::= {lsLcFsuIntervalEntry 12 }
 
         lsLcIntervalMinBwAlloc OBJECT-TYPE
             SYNTAX  INTEGER
    	     ACCESS  read-only
             STATUS  mandatory
             DESCRIPTION
                 "The minimum BW allocation assessed during
		  the current interval."
	   ::= {lsLcFsuIntervalEntry 13 }
 
         lsLcIntervalAvgBwAlloc OBJECT-TYPE
             SYNTAX  INTEGER
    	     ACCESS  read-only
             STATUS  mandatory
             DESCRIPTION
                 "The minimum BW allocation assessed during
		  the current interval."
	   ::= {lsLcFsuIntervalEntry 14 }
 
         lsLcIntervalMaxBwAlloc OBJECT-TYPE
             SYNTAX  INTEGER
    	     ACCESS  read-only
             STATUS  mandatory
             DESCRIPTION
                 "The maximum BW allocation assessed during
		  the current interval."
	   ::= {lsLcFsuIntervalEntry 15 }
 
 
 --	NP STATISTICS SUBSET (Placeholder)

	-- NP Statistics subset definition extensions
	-- These Statistics are yet to be defined.  This reserves a spot for it.
	-- J. Wiggins signed up to do most of this work.
	-- NOTE:  It is not yet clear if we should have NP card identifiers,
	--        is the NP implied by the MIB-view, or can one NP report on
	--	  others?

	 lsNpStatistics OBJECT IDENTIFIER ::= { lsExperimentalStatistics 5 }

-- The following NP CPU workload table is tentative, can be thought of as an example
-- The structure of NP workload statistics is to be defined.  Therefore we provide a table
-- with an uninterpreted variable type index which can specify both the processor and
-- the workload variable of interest.  It is assumed that utilization and other workload
-- statistics of interest can be derived from raw counters.  For instance, if some counters
-- represent number of microseconds of work of the specified type, interval utilization could
-- be derived directly from successive readings.  On the other hand, counts of fixed-cost
-- actions could be used to get a fix on overhead of the specified type, particularly if
-- calibration data were available off-line.

         lsNpCpuWorkloadTable OBJECT-TYPE
    	   SYNTAX  SEQUENCE OF LsNpCpuWorkloadEntry
           ACCESS  not-accessible
	   STATUS  mandatory
	   DESCRIPTION
               "Network processor CPU specific workload statistics"
	   ::= { lsNpStatistics 1 }

	 lsNpCpuWorkloadEntry OBJECT-TYPE
	   SYNTAX   LsNpCpuWorkloadEntry
	   ACCESS   not-accessible
	   STATUS   mandatory
	   DESCRIPTION
	       "An entry in the Network Processor Statistics table."
	   INDEX   { lsNpCpuWorkloadIndex }
	   ::= { lsNpCpuWorkloadTable 1 }

	 LsNpCpuWorkloadEntry ::=
	   SEQUENCE {
	       lsNpCpuWorkloadIndex
	       	INTEGER,
	       lsNpCpuWorkloadEvents
	       	Counter
	       }
    	       	    
         lsNpCpuWorkloadIndex OBJECT-TYPE
             SYNTAX  INTEGER
    	     ACCESS  read-only
             STATUS  mandatory
             DESCRIPTION
                 "Np CPU Workload variable identifier"
         ::= { lsNpCpuWorkloadEntry 1 }

         lsNpCpuWorkloadEvents OBJECT-TYPE
             SYNTAX  Counter
             ACCESS  read-only
             STATUS  mandatory
             DESCRIPTION
    	       	  "NP workload event count"
         ::= { lsNpCpuWorkloadEntry 2 }

--

  lsCellStatistics OBJECT IDENTIFIER ::= { lsExperimentalStatistics 6 }

 -- CEll statistics specific to port and VCI
 -- Double indexing permits us to condition VCI interpretation on the port.

  lsCellVciStatTable OBJECT-TYPE
    SYNTAX  SEQUENCE OF LsCellVciStatEntry
    ACCESS  not-accessible
    STATUS  mandatory
    DESCRIPTION
        "Cell Port/VCI specific statistics subset information"
    ::= { lsCellStatistics 1 }

  lsCellVciStatEntry OBJECT-TYPE
    SYNTAX   LsCellVciStatEntry
    ACCESS   not-accessible
    STATUS   mandatory
    DESCRIPTION
        "An entry in the cell Port/Vci Statistics Table."
    INDEX   { cellVciStatPortIndex, cellVciStatVciIndex }
    ::= { lsCellVciStatTable 1 }

  LsCellVciStatEntry ::=
    SEQUENCE {
        cellVciStatPortIndex
        	INTEGER,
        cellVciStatVciIndex
        	INTEGER,
        cellVciToSwCLP0Cells
        	Counter,
        cellVciToSwCLP01Cells
        	Counter,
        cellVciToSwCLP1Cells
        	Counter,
        cellVciToSwDiscardCells
        	Counter
        }

        	    
  cellVciStatPortIndex OBJECT-TYPE
      SYNTAX  INTEGER
      ACCESS  read-only
      STATUS  mandatory
      DESCRIPTION
                  "This is the ifIndex value of the corresponding
		  ifEntry.  See comments above."
  ::= { lsCellVciStatEntry 1 }


  cellVciStatVciIndex OBJECT-TYPE
      SYNTAX  INTEGER
      ACCESS  read-only
      STATUS  mandatory
      DESCRIPTION
          "Unique Vci identifier for indicated VC"
  ::= { lsCellVciStatEntry 2 }


  cellVciToSwCLP0Cells OBJECT-TYPE
      SYNTAX  Counter
      ACCESS  read-only
      STATUS  mandatory
      DESCRIPTION
          "Number of Cells forwarded to TSU with CLP=0"
  ::= { lsCellVciStatEntry 3 }


  cellVciToSwCLP01Cells OBJECT-TYPE
      SYNTAX  Counter
      ACCESS  read-only
      STATUS  mandatory
      DESCRIPTION
          "Number of Cells forwarded to TSU with CLP=1, which
	   arrived at port as CLP=0."
  ::= { lsCellVciStatEntry 4 }


  cellVciToSwCLP1Cells OBJECT-TYPE
      SYNTAX  Counter
      ACCESS  read-only
      STATUS  mandatory
      DESCRIPTION
          "Number of Cells forwarded to TSU with CLP=1"
  ::= { lsCellVciStatEntry 5 }

  cellVciToSwDiscardCells OBJECT-TYPE
      SYNTAX  Counter
      ACCESS  read-only
      STATUS  mandatory
      DESCRIPTION
          "Number of to-switch Cells discarded due to excessive traffic
 	  according to the Usage Parameter Descriptor for this Vci"
  ::= { lsCellVciStatEntry 6 }

--
--
-- Internal Routing
--


         lsIR                   OBJECT IDENTIFIER ::= { atmSwitch 12 }

	 irRoutingGroup		OBJECT IDENTIFIER ::=	{lsIR 1 }
	 
	 irRoutingPathsGenerated			OBJECT-TYPE
		 SYNTAX	Counter
		 ACCESS	read-only
		 STATUS	mandatory
		 DESCRIPTION
		     "The number of path generation operations performed since
			 initialization."
		 ::= { irRoutingGroup 1 }
	 
	 irRoutingPathGenSuccess			OBJECT-TYPE
		 SYNTAX	Counter
		 ACCESS	read-only
		 STATUS	mandatory
		 DESCRIPTION
		     "The number of path generation operations successfully
			 performed since initialization."
		 ::= { irRoutingGroup 2 }
	 
	 irRoutingPathGenFailedNoResources	OBJECT-TYPE
		 SYNTAX	Counter
		 ACCESS	read-only
		 STATUS	mandatory
		 DESCRIPTION
	     "The number of path generation operations which have failed
			 due to lack of network resources."
		 ::= { irRoutingGroup 3 }
	 
	 irRoutingPathGenFailedUnknown		OBJECT-TYPE
		 SYNTAX	Counter
		 ACCESS	read-only
		 STATUS	mandatory
		 DESCRIPTION
	     "The number of path generation operations which have failed
			 because a specified port or chassis was unknown."
		 ::= { irRoutingGroup 4 }
	 
	 irRoutingPathGenFailedOther		OBJECT-TYPE
		 SYNTAX	Counter
		 ACCESS	read-only
		 STATUS	mandatory
		 DESCRIPTION
	     "The number of path generation operations which have failed
			 for reasons other than unknown chassis/port or lack of
			 network resources."
		 ::= { irRoutingGroup 5 }
	 
	 irRoutingAveragePathLength		OBJECT-TYPE
		 SYNTAX	Counter
		 ACCESS	read-only
		 STATUS	mandatory
		 DESCRIPTION
	     "The average length (in ports) of all paths generated since 
			 initialization."
		 ::= { irRoutingGroup 6 }
	 
         lsStatistics           OBJECT IDENTIFIER ::= { atmSwitch 13 }
--
--
-- TCS Group / Supported by the TMM (TCS Monitoring Module)
--

         tcsInfo             OBJECT IDENTIFIER ::= { atmSwitch 14 }

         tcsTable OBJECT-TYPE
    	    SYNTAX  SEQUENCE OF TcsEntry
            ACCESS  not-accessible
	    STATUS  mandatory
	    DESCRIPTION
                "TCS Slave specific information"
	    ::= { tcsInfo 1 }

	 tcsEntry OBJECT-TYPE
	    SYNTAX   TcsEntry
	    ACCESS   not-accessible
	    STATUS   mandatory
	    DESCRIPTION
	        "An entry in the tcs table ordered by slot. (1-n)"
	    INDEX   { tcsIndex }
	    ::= { tcsTable 1 }

	 TcsEntry ::=
	    SEQUENCE {
	        tcsIndex
	        	INTEGER,
    	        tcsTemp1
    	        	INTEGER,
    	        tcsTemp2
    	        	INTEGER,
    	        tcsTcsVoltage
    	        	INTEGER,
    	        tcsVccVoltage
    	        	INTEGER,
    	        tcsScsiVoltage
    	        	INTEGER,
    	        tcsPostResult
    	        	OCTET STRING (SIZE(6)),
    	    	tcsCardType
    	    	    	INTEGER,
    	    	tcsPaddleTemp1
    	    	    	INTEGER,
    	    	tcsPaddleTemp2
    	    	    	INTEGER,
		tcsPaddleWarnTemp1
			INTEGER,
		tcsPaddleWarnTemp2
			INTEGER,
		tcsPaddleShutdownTemp1
			INTEGER,
		tcsPaddleShutdownTemp2
			INTEGER,
		tcsWarnTemp1
			INTEGER,
		tcsWarnTemp2
			INTEGER,
		tcsShutdownTemp1
			INTEGER,
		tcsShutdownTemp2	
			INTEGER,
		tcsFaultLight
			INTEGER,
		tcsReadyLight
			INTEGER,
	        tcsSwitchConnectivityMask
		        INTEGER
	        }
    	        	    
         tcsIndex OBJECT-TYPE
              SYNTAX  INTEGER
    	      ACCESS  read-only
              STATUS  mandatory
              DESCRIPTION
                  "Unique Index consisting of slot number."
          ::= { tcsEntry 1 }

         tcsTemp1 OBJECT-TYPE
              SYNTAX  INTEGER
    	      ACCESS  read-only
              STATUS  mandatory
              DESCRIPTION
                  "Temperature 1 detected by TCS."
          ::= { tcsEntry 2 }

         tcsTemp2 OBJECT-TYPE
              SYNTAX  INTEGER
    	      ACCESS  read-only
              STATUS  mandatory
              DESCRIPTION
                  "Temperature 2 detected by TCS."
          ::= { tcsEntry 3 }

         tcsTcsVoltage OBJECT-TYPE
              SYNTAX  INTEGER
    	      ACCESS  read-only
              STATUS  mandatory
              DESCRIPTION
                  "Voltage detected by TCS."
          ::= { tcsEntry 4 }

         tcsVccVoltage OBJECT-TYPE
              SYNTAX  INTEGER
    	      ACCESS  read-only
              STATUS  mandatory
              DESCRIPTION
                  "VCC Voltage detected by TCS."
          ::= { tcsEntry 5 }

         tcsScsiVoltage OBJECT-TYPE
              SYNTAX  INTEGER
    	      ACCESS  read-only
              STATUS  mandatory
              DESCRIPTION
                  "SCSI Voltage (or Bulk for switches) detected by TCS."
          ::= { tcsEntry 7 }

         tcsPostResult OBJECT-TYPE
              SYNTAX  OCTET STRING (SIZE(6))
    	      ACCESS  read-only
              STATUS  mandatory
              DESCRIPTION
                  "POST result of card."
          ::= { tcsEntry 8 }

         tcsCardType OBJECT-TYPE
              SYNTAX  INTEGER {
    	    	    empty (1),
    	    	    error (2),
    	    	    unknown (3),
    	    	    switch (4),
    	    	    np (5),
    	    	    lsEdge (6),
    	    	    lsTrunk (7),
    	    	    msTrunk (8),
    	    	    msEdge (10),
		    plc12fac1 (11),  			-- 2-port FDDI
		    plc18eac1 (12),  			--  8-port Ethernet
		    plc1Lstoken (13),			-- Token Ring
		    plc18sac1Edge (14),		-- 8-port Low-speed serial edge
		    plc18sac1Trunk (15),		-- 8-port Low-speed Serial trunk
		    clc1Gen (30),			-- Generic CLC1	
		    clc12oc3ac1Edge (31),		-- 2-port OC3 edge 
		    clc12oc3ac1Trunk (32),		-- 2-port OC3 trunk 
		    clc18t3ac1Edge (33),		-- 8-port T3/E3 edge 
		    clc18t3ac1Trunk (34),		-- 8-port T3/E3 trunk 
		    clc12taxiac1Edge (35),		-- 2-port 155 Mbit TAXI edge 
		    clc12taxiac1Trunk (36),		-- 2-port 155 Mbit TAXI trunk 
		    clc18t1e1cbrac1 (37),		-- 8-port Constant Bit Rate edge 
    	    	    switch2(70)
		    }
    	      ACCESS  read-only
              STATUS  mandatory
              DESCRIPTION
                  "Card type."
          ::= { tcsEntry 9 }

         tcsPaddleTemp1 OBJECT-TYPE
              SYNTAX  INTEGER
    	      ACCESS  read-only
              STATUS  mandatory
              DESCRIPTION
                  "Paddle card temperature 1 detected by TCS."
          ::= { tcsEntry 10 }

         tcsPaddleTemp2 OBJECT-TYPE
              SYNTAX  INTEGER
    	      ACCESS  read-only
              STATUS  mandatory
              DESCRIPTION
                  "Paddle card temperature 2 detected by TCS."
          ::= { tcsEntry 11 }

          tcsPaddleWarnTemp1 OBJECT-TYPE
              SYNTAX  INTEGER
              ACCESS  read-only
              STATUS  mandatory
              DESCRIPTION
                      "Paddle card warning temperature 1 maintained by TCS."
              ::= { tcsEntry 12 }

          tcsPaddleWarnTemp2 OBJECT-TYPE
              SYNTAX  INTEGER
              ACCESS  read-only
              STATUS  mandatory
              DESCRIPTION
                      "Paddle card warning temperature 2 maintained by TCS."
              ::= { tcsEntry 13 }

          tcsPaddleShutdownTemp1 OBJECT-TYPE
              SYNTAX  INTEGER
              ACCESS  read-only
              STATUS  mandatory
              DESCRIPTION
                      "Warning temperature 1 at which the paddle card will
		      shut down."
              ::= { tcsEntry 14 }

          tcsPaddleShutdownTemp2 OBJECT-TYPE
              SYNTAX  INTEGER
              ACCESS  read-only
              STATUS  mandatory
              DESCRIPTION
                      "Warning temperature 2 at which the paddle card will
		      shut down."
              ::= { tcsEntry 15 }

          tcsWarnTemp1 OBJECT-TYPE
              SYNTAX  INTEGER
              ACCESS  read-only
              STATUS  mandatory
              DESCRIPTION
                      "Warning temperature 1 maintained by TCS."
              ::= { tcsEntry 16 }

          tcsWarnTemp2 OBJECT-TYPE
              SYNTAX  INTEGER
              ACCESS  read-only
              STATUS  mandatory
              DESCRIPTION
                      "Warning temperature 2 maintained by TCS."
              ::= { tcsEntry 17 }

          tcsShutdownTemp1 OBJECT-TYPE
              SYNTAX  INTEGER
              ACCESS  read-only
              STATUS  mandatory
              DESCRIPTION
                      "Warning temperature 2 at which the card will
		      shut down." 
              ::= { tcsEntry 18 }

          tcsShutdownTemp2 OBJECT-TYPE
              SYNTAX  INTEGER
              ACCESS  read-only
              STATUS  mandatory
              DESCRIPTION
                      "Warning temperature 2 at which the card will
		      shut down."
              ::= { tcsEntry 19 }

          tcsFaultLight OBJECT-TYPE
              SYNTAX  INTEGER {
			      on(1),
			      off(2)
			      }
              ACCESS  read-only
              STATUS  mandatory
              DESCRIPTION
                      "The state of the fault light."
              ::= { tcsEntry 20 }

          tcsReadyLight OBJECT-TYPE
              SYNTAX  INTEGER {
			      on(1),
			      off(2)
			      }
              ACCESS  read-only
              STATUS  mandatory
              DESCRIPTION
                      "The state of the ready light"
              ::= { tcsEntry 21 }


          tcsSwitchConnectivityMask OBJECT-TYPE
              SYNTAX  INTEGER
              ACCESS  read-only
              STATUS  mandatory
              DESCRIPTION
    	    	"Bitmask of cards with which this function card 
		communicates via the switch.

		Bit 0 is the least-significant bit.  Bit 1 represents
		slot 1, bit 2 represents slot 2 and so on."
		
              ::= { tcsEntry 22 }

         tcsPrimarySwitch OBJECT-TYPE
              SYNTAX  INTEGER {
    	    	    switchA (1),
    	    	    switchB (2)
                    }
    	      ACCESS  read-write
              STATUS  mandatory
              DESCRIPTION
                  "Primary Switch. When 'read' provides the current
    	    	    primary switch. When 'written' attempts to make
    	    	    the written value the new switch."
          ::= { tcsInfo 2 }

         tcsPowerSupplyA OBJECT-TYPE
              SYNTAX  INTEGER {
    	    	    empty (1),
    	    	    failed (2),
    	    	    good (3)
                    }
    	      ACCESS  read-only
              STATUS  mandatory
              DESCRIPTION
    	    	"Status of power supply A."
          ::= { tcsInfo 3 }

         tcsPowerSupplyB OBJECT-TYPE
              SYNTAX  INTEGER {
    	    	    empty (1),
    	    	    failed (2),
    	    	    good (3)
                    }
    	      ACCESS  read-only
              STATUS  mandatory
              DESCRIPTION
    	    	"Status of power supply B."
          ::= { tcsInfo 4 }

         tcsPowerSupplyTypeA OBJECT-TYPE
              SYNTAX  INTEGER {
    	    	    empty (1),
 	    	    dcPowerTray (2),
    	    	    toddPS (3),
                    unknown (4)
                    }
    	      ACCESS  read-only
              STATUS  mandatory
              DESCRIPTION
    	    	"Type of power supply A."
          ::= { tcsInfo 5 }

         tcsPowerSupplyTypeB OBJECT-TYPE
              SYNTAX  INTEGER {
    	    	    empty (1),
    	    	    dcPowerTray (2),
    	    	    toddPS (3),
                    unknown (4)
                    }
    	      ACCESS  read-only
              STATUS  mandatory
              DESCRIPTION
    	    	"Type of power supply A."
          ::= { tcsInfo 6 }


         tcsSwitchFaultMaskA OBJECT-TYPE
              SYNTAX  INTEGER 
    	      ACCESS  read-only
              STATUS  mandatory
              DESCRIPTION
    	    	"Bitmask of slots reporting unhealthy clocks.  If the
		corresponding bit is set, switch card A's clock is
		viewed as unhealthy by the function card in that
		slot. In addition, it indicates whether or not the
		entire switch card has been marked as usable or
		unusable. 

		Bit 1 represents clock health for slot 1, bit 2 
		represents slot 2 and so on. Bit 0 is the 
		least-significant bit.  Bit 0 represents
		the dont-use bit for switch A.  If bit 0 is set, it 
		indicates that TCS has marked switch A as dont-use."
          ::= { tcsInfo 7 }
	


         tcsSwitchFaultMaskB OBJECT-TYPE
              SYNTAX  INTEGER 
    	      ACCESS  read-only
              STATUS  mandatory
              DESCRIPTION
    	    	"Bitmask of slots reporting unhealthy clocks.  If the
		corresponding bit is set, switch card B's clock 
		is viewed as unhealthy by the function card in that
		slot. In addition, it indicates whether or not the
		entire switch card has been marked as usable or
		unusable.

		Bit 1 represents clock health for slot 1, bit 2 
		represents slot 2 and so on. Bit 0 is the 
		least-significant bit.  Bit 0 represents
		the dont-use bit for switch B.  If bit 0 is set, it 
		indicates that TCS has marked switch B as dont-use."  
          ::= { tcsInfo 8 }
	


         tcsSwitchCutoverSupport OBJECT-TYPE
              SYNTAX  INTEGER  {
    	    	    willDoLossLess(1),
    	    	    wontDoLossLess(2),
    	    	    cantDoLossLess(3)
                    }
    	      ACCESS  read-only
              STATUS  mandatory
              DESCRIPTION
    	    	"willDoLossLess indicates that there are two SC2's
		that are in synch.

		wontDoLossLess indicates that there are two SC2's that
		are NOT in sync.

		cantDoLossLess indicates any other situation
		(1-SC1/SC2, 2-SC1's)."
          ::= { tcsInfo 9 }
	


         tcsFCPrimarySwitchA OBJECT-TYPE
              SYNTAX  INTEGER 
    	      ACCESS  read-only
              STATUS  mandatory
              DESCRIPTION
    	    	"The bit corresponding to that slot is a 1 if the card
		believes that Switch A is the primary switch and 0
		otherwise.

		Bit 0 is the least-significant bit.  Bit 1 represents
		slot 1, bit 2 represents slot 2 and so on."
          ::= { tcsInfo 10 }
	


         tcsFCPrimarySwitchB OBJECT-TYPE
              SYNTAX  INTEGER 
    	      ACCESS  read-only
              STATUS  mandatory
              DESCRIPTION
    	    	"The bit corresponding to that slot is a 1 if the card
		believes that Switch B is the primary switch and 0
		otherwise.

		Bit 0 is the least-significant bit.  Bit 1 represents
		slot 1, bit 2 represents slot 2 and so on."
          ::= { tcsInfo 11 }
	


--
--
-- Global (?) objects
--   
         lsGID          OBJECT IDENTIFIER ::= { atmSwitch 15 }

-- 
	-- Generic GID Variables
-- 

gidGeneralGroup 	OBJECT IDENTIFIER ::= { lsGID 1 }

gidSoftwareVersionNumber		OBJECT-TYPE
	SYNTAX	DisplayString
	ACCESS	read-only
	STATUS	mandatory
	DESCRIPTION
	    "The global information distribution (GID) process software
		revision number" 
	::= { gidGeneralGroup 1 }

gidProcessID				OBJECT-TYPE
	SYNTAX	INTEGER
	ACCESS	read-only
	STATUS	mandatory
	DESCRIPTION
	    "The GID process ID."
	::= { gidGeneralGroup 2 }

gidUpTime				OBJECT-TYPE
	SYNTAX	INTEGER
	ACCESS	read-only
	STATUS	mandatory
	DESCRIPTION
	    "The number of seconds the GID process has been running."
	::= { gidGeneralGroup 3 }

gidMemoryUse				OBJECT-TYPE
	SYNTAX	Counter
	ACCESS	read-only
	STATUS	mandatory
	DESCRIPTION
	    "The total amount of memory (in bytes) currently allocated
		by GID for all purposes."
	::= { gidGeneralGroup 4 }

gidTimersProcessed			OBJECT-TYPE
	SYNTAX	Counter
	ACCESS	read-only
	STATUS	mandatory
	DESCRIPTION
	    "The number of timers processed by the GID process
		since initialization."
	::= { gidGeneralGroup 5 }

gidMallocFailures			OBJECT-TYPE
	SYNTAX	Counter
	ACCESS	read-only
	STATUS	mandatory
	DESCRIPTION
	    "The number of times GID has failed to dynamically
		allocate memory since initialization."
	::= { gidGeneralGroup 6 }

gidDebugFlag			OBJECT-TYPE
	SYNTAX	INTEGER
	ACCESS	read-write
	STATUS	mandatory
	DESCRIPTION
	    "Bit mask for debug statements to AppLog.  This is being
	    used for debug purposes.  It is not advised that the
	    user change this.  Future releases may move this to a
	    debug subtree."
	::= { gidGeneralGroup 7 }


gidDebugLevel			OBJECT-TYPE
	SYNTAX	INTEGER
	ACCESS	read-write
	STATUS	mandatory
	DESCRIPTION
	    "The gidDebugLevel determines the amount of detail that
	    the debug flags will cause to dump to the apps.log, where
	    0 means no detail and 3 is the maximum value

	    Future releases may move this to a debug subtree."
	::= { gidGeneralGroup 8 }


gidAcceptedBcastRateIn			OBJECT-TYPE
	SYNTAX	INTEGER
	ACCESS	read-write
	STATUS	mandatory
	DESCRIPTION
	    "The LAN inbound broadcast traffic average inter-frame
	    time specified in microseconds.  The default rate is
	    20,000 microseconds.

	    Defines the acceptable average inbound bcast rate.
	    
	    Future releases may move this to another subtree."
	::= { gidGeneralGroup 9 }


--
-- 
-- GID Neighbor Variables
-- 

gidNbrGroup 		OBJECT IDENTIFIER ::= { lsGID 2 }

gidNbrCount				OBJECT-TYPE
	SYNTAX	Counter
	ACCESS	read-only
	STATUS	mandatory
	DESCRIPTION
	    "The number of neighbor NPs known to the GID process."
	::= { gidNbrGroup 1 }

gidNbrTable				OBJECT-TYPE
	SYNTAX	SEQUENCE OF GidNbrEntry
	ACCESS  not-accessible
	STATUS	mandatory
	DESCRIPTION
	    "A table containing information about each GID neighbor."
	::= { gidNbrGroup 2 }

gidNbrEntry				OBJECT-TYPE
	SYNTAX	GidNbrEntry
	ACCESS	not-accessible
	STATUS	mandatory
	DESCRIPTION
	    "The information regarding a single GID neighbor."
	INDEX	{ gidNbrEIA }
	::= { gidNbrTable 1 }

GidNbrEntry ::=
	SEQUENCE {
	    gidNbrEIA				INTEGER,
	    gidNbrVCI				INTEGER,
	    gidNbrState				INTEGER,
	    gidNbrSyncEvents			Counter,
	    gidNbrDBReqListLength		Counter,
	    gidNbrDBSumListLength		Counter,
	    gidNbrHellosRx			Counter,
	    gidNbrLinkAnnouncementsRx		Counter,
	    gidNbrNewLinkAnnouncementsRx	Counter,
	    gidNbrIPAnnouncementsRx		Counter,
	    gidNbrNewIPAnnouncementsRx		Counter,
	    gidNbrGenericAnnouncementsRx	Counter,
	    gidNbrNewGenericAnnouncementsRx	Counter
	}

gidNbrEIA				OBJECT-TYPE
	SYNTAX	INTEGER
	ACCESS	read-only
	STATUS	mandatory
	DESCRIPTION
	    "The internal address of the neighbor NP."
	::= {gidNbrEntry 1 }

gidNbrVCI				OBJECT-TYPE
	SYNTAX	INTEGER	
	ACCESS	read-only
	STATUS	mandatory
	DESCRIPTION
	    "The VCI of the reliable channel to the neighbor."
	::= {gidNbrEntry 2 }

gidNbrState				OBJECT-TYPE
	SYNTAX	INTEGER {
		    unknown	(1),
		    existent	(2),
		    exstart	(3),
		    exchange	(4),
		    loading	(5),
		    full	(6)
		}
	ACCESS	read-only
	STATUS	mandatory
	DESCRIPTION
	    "The neighbor's synchronization protocol state."
	::= {gidNbrEntry 3 }

gidNbrSyncEvents			OBJECT-TYPE
	SYNTAX	Counter
	ACCESS	read-only
	STATUS	mandatory
	DESCRIPTION
	    "The number of synchronization protocol events associated
		with this neighbor that have occurred since
		initialization." 
	::= {gidNbrEntry 4 }

gidNbrDBReqListLength			OBJECT-TYPE
	SYNTAX	Counter
	ACCESS	read-only
	STATUS	mandatory
	DESCRIPTION
	    "The number of database requests queued to the neighbor."
	::= {gidNbrEntry 5 }

gidNbrDBSumListLength			OBJECT-TYPE
	SYNTAX	Counter
	ACCESS	read-only
	STATUS	mandatory
	DESCRIPTION
	    "The number of database summary list entries queued for
		transmission to the neighbor."
	::= {gidNbrEntry 6 }

gidNbrHellosRx				OBJECT-TYPE
	SYNTAX	Counter
	ACCESS	read-only
	STATUS	mandatory
	DESCRIPTION
	    "The number of Hello packets received from the neighbor."
	::= {gidNbrEntry 7 }

gidNbrLinkAnnouncementsRx		OBJECT-TYPE
	SYNTAX	Counter
	ACCESS	read-only
	STATUS	mandatory
	DESCRIPTION
	    "The number of link state announcements received from the
		neighbor." 
	::= {gidNbrEntry 8 }

gidNbrNewLinkAnnouncementsRx		OBJECT-TYPE
	SYNTAX	Counter
	ACCESS	read-only
	STATUS	mandatory
	DESCRIPTION
	    "The number of link state announcements received from the
		neighbor and accepted as new."
	::= {gidNbrEntry 9 }

gidNbrIPAnnouncementsRx			OBJECT-TYPE
	SYNTAX	Counter
	ACCESS	read-only
	STATUS	mandatory
	DESCRIPTION
	    "The number of internal IP address translation announcements
		received from the neighbor." 
	::= {gidNbrEntry 10 }

gidNbrNewIPAnnouncementsRx		OBJECT-TYPE
	SYNTAX	Counter
	ACCESS	read-only
	STATUS	mandatory
	DESCRIPTION
	    "The number of internal IP address translation announcements
		received from the neighbor and accepted as new."
	::= {gidNbrEntry 11 }

gidNbrGenericAnnouncementsRx		OBJECT-TYPE
	SYNTAX	Counter
	ACCESS	read-only
	STATUS	mandatory
	DESCRIPTION
	    "The number of generic global information announcements
		received from the neighbor."
	::= {gidNbrEntry 12 }

gidNbrNewGenericAnnouncementsRx		OBJECT-TYPE
	SYNTAX	Counter
	ACCESS	read-only
	STATUS	mandatory
	DESCRIPTION
	    "The number of generic global information  announcements
		received from the neighbor and accepted as new."
	::= {gidNbrEntry 13 }

--
-- 
-- GID Client Variables
-- 

gidClientGroup 		OBJECT IDENTIFIER ::= { lsGID 3 }

gidClientCount				OBJECT-TYPE
	SYNTAX	Counter
	ACCESS	read-only
	STATUS	mandatory
	DESCRIPTION
	    "The number of registered GID client processes."
	::= { gidClientGroup 1 }

gidClientTable				OBJECT-TYPE
	SYNTAX	SEQUENCE OF GidClientEntry
	ACCESS	not-accessible
	STATUS	mandatory
	DESCRIPTION
	    "A table containing information about each GID client process."
	::= { gidClientGroup 2 }

gidClientEntry				OBJECT-TYPE
	SYNTAX	GidClientEntry
	ACCESS	not-accessible
	STATUS	mandatory
	DESCRIPTION
	    "The information regarding a single GID client process."
	INDEX	{ gidClientID }
	::= { gidClientTable 1 }

GidClientEntry ::=
	SEQUENCE {
	    gidClientID				INTEGER,
	    gidClientEIA			INTEGER,
	    gidClientAnnouncementsRx		Counter,
	    gidClientLinkAnnouncementsRx	Counter,
	    gidClientIPAnnouncementsRx		Counter,
	    gidClientGenericAnnouncementsRx	Counter,
	    gidClientEventsTx			Counter,
	    gidClientPathsGenerated		Counter
	}

gidClientID				OBJECT-TYPE
	SYNTAX	INTEGER
	ACCESS	read-only
	STATUS	mandatory
	DESCRIPTION
	    "The GID client process identifier."
	::= { gidClientEntry 1 }

gidClientEIA				OBJECT-TYPE
	SYNTAX	INTEGER
	ACCESS	read-only
	STATUS	mandatory
	DESCRIPTION
	    "The internal card address associated with the
		GID client process.

		Edge and trunk card control processes are associated
		with a unique card address.  The NP card control process
		and the Congestion Avoidance information distribution
		process share the internal card address of the local
		NP."
	::= { gidClientEntry 2 }

gidClientAnnouncementsRx		OBJECT-TYPE
	SYNTAX	Counter
	ACCESS	read-only
	STATUS	mandatory
	DESCRIPTION
	    "The total number of global information announcements
		received from this GID client process since
		initialization." 
	::= { gidClientEntry 3 }

gidClientLinkAnnouncementsRx		OBJECT-TYPE
	SYNTAX	Counter
	ACCESS	read-only
	STATUS	mandatory
	DESCRIPTION
	    "The number of link state information announcements
		received from this GID client process since
		initialization." 
	::= { gidClientEntry 4 }

gidClientIPAnnouncementsRx		OBJECT-TYPE
	SYNTAX	Counter
	ACCESS	read-only
	STATUS	mandatory
	DESCRIPTION
	    "The number of internal IP address translation announcements
		received from this GID client process since
		initialization."
	::= { gidClientEntry 5 }

gidClientGenericAnnouncementsRx		OBJECT-TYPE
	SYNTAX	Counter
	ACCESS	read-only
	STATUS	mandatory
	DESCRIPTION
	    "The number of generic global information announcements
		received from this GID client process since
		initialization."  
	::= { gidClientEntry 6 }

gidClientEventsTx			OBJECT-TYPE
	SYNTAX	Counter
	ACCESS	read-only
	STATUS	mandatory
	DESCRIPTION
	    "The number of global information-related events sent by the
		GID process to the GID client process since
		initialization."
	::= { gidClientEntry 7 }

gidClientPathsGenerated			OBJECT-TYPE
	SYNTAX	Counter
	ACCESS	read-only
	STATUS	mandatory
	DESCRIPTION
	    "The number of path generation requests made by the GID
		client process since initialization."
	::= { gidClientEntry 8 }


--	
-- 
-- GID I/O Variables
-- 
gidIOGroup		OBJECT IDENTIFIER ::= { lsGID 4 }

gidIONbrMsgBuffersFree			OBJECT-TYPE
	SYNTAX	Counter
	ACCESS	read-only
	STATUS	mandatory
	DESCRIPTION
	    "The number of neighbor message buffers available on the
		neighbor message buffer free list."
	::= { gidIOGroup 1 }

gidIONbrMsgBuffersActive		OBJECT-TYPE
	SYNTAX	Counter
	ACCESS	read-only
	STATUS	mandatory
	DESCRIPTION
	    "The number of neighbor message buffers currently active,
		either in transmission or queued for output."
	::= { gidIOGroup 2 }

gidIOClientMsgBuffersFree		OBJECT-TYPE
	SYNTAX	Counter
	ACCESS	read-only
	STATUS	mandatory
	DESCRIPTION
	    "The number of client message buffers available on the
		client message buffer free list."
	::= { gidIOGroup 3 }

gidIOClientMsgBuffersActive		OBJECT-TYPE
	SYNTAX	Counter
	ACCESS	read-only
	STATUS	mandatory
	DESCRIPTION
	    "The number of client message buffers currently active,
		either in transmission or queued for output."
	::= { gidIOGroup 4 }



--
-- 
-- Database Synchronization Protocol Variables
-- 

gidSyncGroup		OBJECT IDENTIFIER ::= { lsGID 6 }

gidSyncNbrsExistent			OBJECT-TYPE
	SYNTAX	Counter
	ACCESS	read-only
	STATUS	mandatory
	DESCRIPTION
	    "The number of neighbors in the Existent synchronization
		protocol state."
	::= { gidSyncGroup 1 }

gidSyncNbrsExStart			OBJECT-TYPE
	SYNTAX	Counter
	ACCESS	read-only
	STATUS	mandatory
	DESCRIPTION
	    "The number of neighbors in the Exchange Start
		synchronization protocol state."
	::= { gidSyncGroup 2 }

gidSyncNbrsExchange			OBJECT-TYPE
	SYNTAX	Counter
	ACCESS	read-only
	STATUS	mandatory
	DESCRIPTION
	    "The number of neighbors in the Exchange synchronization
		protocol state."
	::= { gidSyncGroup 3 }

gidSyncNbrsLoading			OBJECT-TYPE
	SYNTAX	Counter
	ACCESS	read-only
	STATUS	mandatory
	DESCRIPTION
	    "The number of neighbors in the Loading synchronization
		protocol state."
	::= { gidSyncGroup 4 }

gidSyncNbrsFull				OBJECT-TYPE
	SYNTAX	Counter
	ACCESS	read-only
	STATUS	mandatory
	DESCRIPTION
	    "The number of neighbors in the Full synchronization protocol
		state."
	::= { gidSyncGroup 5 }


--
-- 
-- Link State Database Variables
-- 
	
gidLinkGroup 		OBJECT IDENTIFIER ::= { lsGID 7 }

gidLinkDatabaseSize		OBJECT-TYPE
	SYNTAX	INTEGER
	ACCESS	read-only
	STATUS	mandatory
	DESCRIPTION
	    "The current size of the link state database, in bytes."
	::= { gidLinkGroup 1 }


-- GID LSDB Line Card Structure

gidLineCardTable			OBJECT-TYPE
	SYNTAX	SEQUENCE OF GidLineCardEntry
	ACCESS	not-accessible
	STATUS	mandatory
	DESCRIPTION
	    "A table containing information about each line card
		known to GID."		
	::= { gidLinkGroup 2 }

gidLineCardEntry			OBJECT-TYPE
	SYNTAX	GidLineCardEntry
	ACCESS	not-accessible
	STATUS	mandatory
	DESCRIPTION
	    "The information regarding a single line card."
	INDEX	{ gidLineCardChassis, gidLineCardSlot }
	::= { gidLineCardTable 1 }

GidLineCardEntry ::=
	SEQUENCE {
	    gidLineCardChassis			INTEGER,
	    gidLineCardSlot			INTEGER,
	    gidLineCardEntryAge			LightStreamUpToMaxAge,
	    gidLineCardEntrySeqno		INTEGER,
	    gidLineCardEntryAdvNP		INTEGER,
	    gidLineCardPorts			INTEGER
	}


-- Elements in the Line Card Structure

gidLineCardChassis			OBJECT-TYPE
	SYNTAX	INTEGER
	ACCESS	read-only
	STATUS	mandatory
	DESCRIPTION
	    "The internal chassis ID of the chassis which contains the
		line card described by the link state entry."
	::= { gidLineCardEntry 1 }

gidLineCardSlot				OBJECT-TYPE
	SYNTAX	INTEGER
	ACCESS	read-only
	STATUS	mandatory
	DESCRIPTION
	    "The slot in the chassis which contains the line card
		described by the link state entry."
	::= { gidLineCardEntry 2 }

gidLineCardEntryAge			OBJECT-TYPE
	SYNTAX	LightStreamUpToMaxAge
	ACCESS	read-only
	STATUS	mandatory
	DESCRIPTION
	    "The time, in seconds, that have elapsed since the link
		state advertisement was originated.

	    The link state advertisement will be purged from the global
		database when the age reaches MaxAge (1 hour)."
	::= { gidLineCardEntry 3 }

gidLineCardEntrySeqno			OBJECT-TYPE
	SYNTAX	INTEGER
	ACCESS	read-only
	STATUS	mandatory
	DESCRIPTION
	    "The flooding protocol sequence number currently associated
		with the link state advertisement.  The sequence number
		is a signed 32-bit integer.  It is used to detect old
		and duplicate database announcements.  The sequence 
		number space is linearly ordered; the larger the
		sequence number, the more recent the database
		announcement." 
	::= { gidLineCardEntry 4 }

gidLineCardEntryAdvNP			OBJECT-TYPE
	SYNTAX	INTEGER
	ACCESS	read-only
	STATUS	mandatory
	DESCRIPTION
	    "The internal card ID of the Network Processor which
		originated the IP address translation." 
	::= { gidLineCardEntry 5 }


gidLineCardPorts			OBJECT-TYPE
	SYNTAX	INTEGER
	ACCESS	read-only
	STATUS	mandatory
	DESCRIPTION
	    "The number of edge and/or trunk ports attached to the line
		card.  Network processor cards may be advertised as
		having 0 ports."
	::= { gidLineCardEntry 6 }



-- GID LSDB Port Structure

gidPortTable				OBJECT-TYPE
	SYNTAX	SEQUENCE OF GidPortEntry
	ACCESS	not-accessible
	STATUS	mandatory
	DESCRIPTION
	    "A table containing information about each network link
		known to GID.

	    A point-to-point link is represented by two entries in the
	    GID link state database, one for each direction of
	    data transmission."
	::= { gidLinkGroup 3 }

gidPortEntry				OBJECT-TYPE
	SYNTAX	GidPortEntry
	ACCESS	not-accessible
	STATUS	mandatory
	DESCRIPTION
	    "The information regarding a single network link."
	INDEX	{ gidPortChassis, gidPortID }
	::= { gidPortTable 1 }

GidPortEntry ::=
	SEQUENCE {
	    gidPortChassis		INTEGER,
	    gidPortID			INTEGER,
	    gidPortService		INTEGER,
	    gidPortUpDown		INTEGER,
	    gidPortBW0			INTEGER,
	    gidPortBW1			INTEGER,
	    gidPortBW2			INTEGER,
	    gidPortRemoteChassis	INTEGER,
	    gidPortRemotePort		INTEGER
	}

-- Elements in the Port Structure

gidPortChassis				OBJECT-TYPE
	SYNTAX	INTEGER
	ACCESS	read-only
	STATUS	mandatory
	DESCRIPTION
	    "The internal chassis ID of the chassis which contains the
		line card associated with the port."
	::= { gidPortEntry 1 }

gidPortID				OBJECT-TYPE
	SYNTAX	INTEGER
	ACCESS	read-only
	STATUS	mandatory
	DESCRIPTION
                  "This is the ifIndex value of the corresponding
		  ifEntry.  See comments above."
	::= { gidPortEntry 2 }

gidPortService				OBJECT-TYPE
	SYNTAX	INTEGER {
		    trunk (1),
		    edge  (2)
		}
	ACCESS	read-only
	STATUS	mandatory
	DESCRIPTION
	    "The operating mode (trunk or edge) of the port."
	::= { gidPortEntry 3 }

gidPortUpDown				OBJECT-TYPE
	SYNTAX	INTEGER {
		    down (1),
		    up   (2)
		}
	ACCESS	read-only
	STATUS	mandatory
	DESCRIPTION
	    "The up/down state of the port."
	::= { gidPortEntry 4 }

gidPortBW0				OBJECT-TYPE
	SYNTAX	INTEGER
	ACCESS	read-only
	STATUS	mandatory
	DESCRIPTION
	    "The amount of type 0 bandwidth available for reservation
		for data transmission through the port."
	::= { gidPortEntry 5 }

gidPortBW1				OBJECT-TYPE
	SYNTAX	INTEGER
	ACCESS	read-only
	STATUS	mandatory
	DESCRIPTION
	    "The amount of type 1 bandwidth available for reservation
		for data transmission through the port."
	::= { gidPortEntry 6 }

gidPortBW2				OBJECT-TYPE
	SYNTAX	INTEGER
	ACCESS	read-only
	STATUS	mandatory
	DESCRIPTION
	    "The amount of type 2 bandwidth available for reservation
		for data transmission through the port."
	::= { gidPortEntry 7 }

gidPortRemoteChassis			OBJECT-TYPE
	SYNTAX	INTEGER
	ACCESS	read-only
	STATUS	mandatory
	DESCRIPTION
	    "The internal chassis ID of the chassis which contains the
		line card and port at the remote end of the
		point-to-point link." 
	::= { gidPortEntry 8 }

gidPortRemotePort			OBJECT-TYPE
	SYNTAX	INTEGER
	ACCESS	read-only
	STATUS	mandatory
	DESCRIPTION
                  "This is the ifIndex value of the corresponding
		  ifEntry.  See comments above."
	::= { gidPortEntry 9 }


--
-- 
-- Address Translation Database Variables
--
	
gidIpAddressGroup 	OBJECT IDENTIFIER ::= { lsGID 8 }

gidIpAddressDatabaseSize		OBJECT-TYPE
	SYNTAX	INTEGER
	ACCESS	read-only
	STATUS	mandatory
	DESCRIPTION
	    "The current size of the address translation database, in
		bytes."
	::= { gidIpAddressGroup 1 }

gidIpAddressTable			OBJECT-TYPE
	SYNTAX	SEQUENCE OF GidIpAddressEntry
	ACCESS	not-accessible
	STATUS	mandatory
	DESCRIPTION
	    "A table containing information about each internal IP
		address translation known to GID."		
	::= { gidIpAddressGroup 2 }

gidIpAddressEntry			OBJECT-TYPE
	SYNTAX	GidIpAddressEntry
	ACCESS	not-accessible
	STATUS	mandatory
	DESCRIPTION
	    "The information regarding a single internal IP address
		translation."
	INDEX	{ gidInternalIpAddress }
	::= { gidIpAddressTable 1 }

GidIpAddressEntry ::=
	SEQUENCE {
	    gidInternalIpAddress		IpAddress,
	    gidIpEntryAge			LightStreamUpToMaxAge,
	    gidIpEntrySeqno			INTEGER,
	    gidIpEntryAdvNP			INTEGER,
	    gidIpEntryNetMask			INTEGER,
	    gidIpEntryEIA			OCTET STRING (SIZE(6))
	}

-- Elements in the IP Address Translation Structure

gidInternalIpAddress			OBJECT-TYPE
	SYNTAX	IpAddress
	ACCESS	read-only
	STATUS	mandatory
	DESCRIPTION
	    "The internal IP address associated with the IP
		address translation instance."
	::= { gidIpAddressEntry 1 }

gidIpEntryAge				OBJECT-TYPE
	SYNTAX	LightStreamUpToMaxAge
	ACCESS	read-only
	STATUS	mandatory
	DESCRIPTION
	    "The time, in seconds, that have elapsed since the IP address
		translation was originated.

	    The address translation will be purged from the global
		database when the age reaches MaxAge (1 hour)."

	::= { gidIpAddressEntry 2 }

gidIpEntrySeqno				OBJECT-TYPE
	SYNTAX	INTEGER
	ACCESS	read-only
	STATUS	mandatory
	DESCRIPTION
	    "The flooding protocol sequence number currently associated
		with the IP address translation. The sequence number
		is a signed 32-bit integer.  It is used to detect old
		and duplicate database announcements.  The sequence 
		number space is linearly ordered; the larger the
		sequence number, the more recent the database
		announcement." 
	::= { gidIpAddressEntry 3 }

gidIpEntryAdvNP				OBJECT-TYPE
	SYNTAX	INTEGER
	ACCESS	read-only
	STATUS	mandatory
	DESCRIPTION
	    "The internal card ID of the Network Processor which
		originated the IP address translation." 
	::= { gidIpAddressEntry 4 }

gidIpEntryNetMask			OBJECT-TYPE
	SYNTAX	INTEGER
	ACCESS	read-only
	STATUS	mandatory
	DESCRIPTION
	    "The IP network mask associated with the IP address
		translation."
	::= { gidIpAddressEntry 5 }

gidIpEntryEIA				OBJECT-TYPE
	SYNTAX	OCTET STRING (SIZE(6))
	ACCESS	read-only
	STATUS	mandatory
	DESCRIPTION
	    "The internal address of the network port associated with
		the IP address translation."
	::= { gidIpAddressEntry 6 }


--
-- 
-- Event Registration & Notification Variables
-- 

gidEventGroup		OBJECT IDENTIFIER ::= { lsGID 9 }


gidEventLinkEventsDelivered		OBJECT-TYPE
	SYNTAX	Counter
	ACCESS	read-only
	STATUS	mandatory
	DESCRIPTION
	    "The number of link events delivered by GID since
		initialization."
	::= { gidEventGroup 1 }

gidEventIpEventsDelivered		OBJECT-TYPE
	SYNTAX	Counter
	ACCESS	read-only
	STATUS	mandatory
	DESCRIPTION
	    "The number of internal IP events delivered by GID since
		initialization."
	::= { gidEventGroup 2 }

gidEventGenericGinfoEventsDelivered	OBJECT-TYPE
	SYNTAX	Counter
	ACCESS	read-only
	STATUS	mandatory
	DESCRIPTION
	    "The number of generic global information events delivered
		by GID since initialization."
	::= { gidEventGroup 3 }


-- Generic Global Information Event Counts
-- 
-- One bucket per distribution group 

gidEventGenericGinfoEventTable		OBJECT-TYPE
	SYNTAX	SEQUENCE OF GidEventGenericGinfoEventCount
	ACCESS	not-accessible
	STATUS	mandatory
	DESCRIPTION
	    "A table containing the number of generic global
		information events transmitted by GID since
		initialization.  The table is indexed by 
		distribution group."
	::= { gidEventGroup 4 }

gidEventGenericGinfoEventCount		OBJECT-TYPE
	SYNTAX	GidEventGenericGinfoEventCount
	ACCESS	not-accessible
	STATUS	mandatory
	DESCRIPTION
	    "The number of generic global information events delivered
		to clients in this distribution group."
	INDEX { gidEventDistributionGroup }
	::= { gidEventGenericGinfoEventTable 1 }

GidEventGenericGinfoEventCount ::=
	SEQUENCE {
	    gidEventDistributionGroup		INTEGER,
	    gidEventGenericGinfoEvents		Counter
	}
	
gidEventDistributionGroup		OBJECT-TYPE
	SYNTAX	INTEGER
	ACCESS	read-only
	STATUS	mandatory
	DESCRIPTION
	    "The flooding protocol distribution group to which the
		events were delivered." 
	::= { gidEventGenericGinfoEventCount 1 }

gidEventGenericGinfoEvents		OBJECT-TYPE
	SYNTAX	Counter
	ACCESS	read-only
	STATUS	mandatory
	DESCRIPTION
	    "The number of events delivered to clients in the
		distribution group."
	::= { gidEventGenericGinfoEventCount 2 }


--
-- 
-- OS-Process oriented Objects
-- 

         lsPID          OBJECT IDENTIFIER ::= { atmSwitch 16	}

         pidTable OBJECT-TYPE
    	    SYNTAX  SEQUENCE OF PidEntry
            ACCESS  not-accessible
	    STATUS  mandatory
	    DESCRIPTION
                "PID table of current pids"
	    ::= { lsPID 1 }

	 pidEntry OBJECT-TYPE
	    SYNTAX   PidEntry
	    ACCESS   not-accessible
	    STATUS   mandatory
	    DESCRIPTION
	        "An entry in the PPID table."
	    INDEX   { pidIndex }
	    ::= { pidTable 1 }

	 PidEntry ::=
	    SEQUENCE {
	        pidIndex
	        	INTEGER,
    	    	pidName
    	    	    	DisplayString,
    	    	pidCreationTime
    	    	    	INTEGER,
    	    	pidOperStatus
    	    	    	INTEGER,
    	    	pidAdminStatus
    	    	    	INTEGER
	        }
    	        	    
         pidIndex OBJECT-TYPE
              SYNTAX  INTEGER
    	      ACCESS  read-only
              STATUS  mandatory
              DESCRIPTION
                  "Unique Index consisting of PID number."
          ::= { pidEntry 1 }

         pidName OBJECT-TYPE
              SYNTAX  DisplayString
    	      ACCESS  read-only
              STATUS  mandatory
              DESCRIPTION
                  "Process Name."
          ::= { pidEntry 2 }

         pidCreationTime OBJECT-TYPE
              SYNTAX  INTEGER
    	      ACCESS  read-only
              STATUS  mandatory
              DESCRIPTION
                  "Time since process creation in seconds."
          ::= { pidEntry 3 }

         pidOperStatus OBJECT-TYPE
              SYNTAX  INTEGER {
    	    	    	up (1),
    	    	    	down (2)
    	    	    	}
    	      ACCESS  read-only
              STATUS  mandatory
              DESCRIPTION
                  "Operation Status of process."
          ::= { pidEntry 4 }

         pidAdminStatus OBJECT-TYPE
              SYNTAX  INTEGER {
    	    	    	up (1),
    	    	    	down (2)
    	    	    	}
    	      ACCESS  read-write
              STATUS  mandatory
              DESCRIPTION
                  "Administratively desired state of process."
          ::= { pidEntry 5 }


--
-- 
-- NeighborHood Discovery Objects
-- 

         lsND           OBJECT IDENTIFIER ::= { atmSwitch 17 }

ndGeneralGroup 	OBJECT IDENTIFIER ::= { lsND 1 }

ndSoftwareVersionNumber			OBJECT-TYPE
	SYNTAX	DisplayString
	ACCESS	read-only
	STATUS	mandatory
	DESCRIPTION
	    "The neighborhood discovery (ND) process software
		revision number" 
	::= { ndGeneralGroup 1 }

ndProcessID				OBJECT-TYPE
	SYNTAX	INTEGER
	ACCESS	read-only
	STATUS	mandatory
	DESCRIPTION
	    "The ND process ID."
	::= { ndGeneralGroup 2 }

ndMemoryUse				OBJECT-TYPE
	SYNTAX	Counter
	ACCESS	read-only
	STATUS	mandatory
	DESCRIPTION
	    "The total amount of dynamically allocated memory (in
		bytes) currently allocated by the ND process for
		all purposes."
	::= { ndGeneralGroup 4 }

ndTimersProcessed			OBJECT-TYPE
	SYNTAX	Counter
	ACCESS	read-only
	STATUS	mandatory
	DESCRIPTION
	    "The number of timers processed by the ND process
		since initialization."
	::= { ndGeneralGroup 5 }

--
-- 
-- ND Managed Line Card Variables
-- 

ndLCGroup 		OBJECT IDENTIFIER ::= { lsND 2 }

ndLCCount				OBJECT-TYPE
	SYNTAX	Counter
	ACCESS	read-only
	STATUS	mandatory
	DESCRIPTION
	    "The number of line cards managed by the NP."
	::= { ndLCGroup 1 }

ndLCTable				OBJECT-TYPE
	SYNTAX	SEQUENCE OF NdLCEntry
	ACCESS  not-accessible
	STATUS	mandatory
	DESCRIPTION
	    "A table containing information about each managed line
		card neighbor."
	::= { ndLCGroup 2 }

ndLCEntry				OBJECT-TYPE
	SYNTAX	NdLCEntry
	ACCESS	not-accessible
	STATUS	mandatory
	DESCRIPTION
	    "The information regarding a single ND neighbor."
	INDEX	{ ndLCEIA }
	::= { ndLCTable 1 }

NdLCEntry ::=
	SEQUENCE {
	    ndLCEIA				INTEGER,
	    ndLCChannel				INTEGER,
	    ndLCState				INTEGER
	}

ndLCEIA					OBJECT-TYPE
	SYNTAX	INTEGER
	ACCESS	read-only
	STATUS	mandatory
	DESCRIPTION
	    "The internal address of the managed line card."
	::= {ndLCEntry 1 }

ndLCChannel				OBJECT-TYPE
	SYNTAX	INTEGER	
	ACCESS	read-only
	STATUS	mandatory
	DESCRIPTION
	    "The reliable channel to the managed line card."
	::= {ndLCEntry 2 }

ndLCState				OBJECT-TYPE
	SYNTAX	INTEGER {
		    unknown	(1),
		    existent	(2),
		    up		(3),
		    comingdown  (4)
		}
	ACCESS	read-only
	STATUS	mandatory
	DESCRIPTION
	    "The line card's state."
	::= {ndLCEntry 3 }

--
-- 
-- ND Neighbor Variables
-- 

ndNbrGroup 		OBJECT IDENTIFIER ::= { lsND 3 }

ndNbrCount				OBJECT-TYPE
	SYNTAX	Counter
	ACCESS	read-only
	STATUS	mandatory
	DESCRIPTION
	    "The number of neighbor NPs known to the ND process."
	::= { ndNbrGroup 1 }

ndNbrTable				OBJECT-TYPE
	SYNTAX	SEQUENCE OF NdNbrEntry
	ACCESS  not-accessible
	STATUS	mandatory
	DESCRIPTION
	    "A table containing information about each ND neighbor."
	::= { ndNbrGroup 2 }

ndNbrEntry				OBJECT-TYPE
	SYNTAX	NdNbrEntry
	ACCESS	not-accessible
	STATUS	mandatory
	DESCRIPTION
	    "The information regarding a single ND neighbor."
	INDEX	{ ndNbrEIA }
	::= { ndNbrTable 1 }

NdNbrEntry ::=
	SEQUENCE {
	    ndNbrEIA				INTEGER,
	    ndNbrChannel			INTEGER,
	    ndNbrState				INTEGER
	}

ndNbrEIA				OBJECT-TYPE
	SYNTAX	INTEGER
	ACCESS	read-only
	STATUS	mandatory
	DESCRIPTION
	    "The internal address of the neighbor NP."
	::= {ndNbrEntry 1 }

ndNbrChannel				OBJECT-TYPE
	SYNTAX	INTEGER	
	ACCESS	read-only
	STATUS	mandatory
	DESCRIPTION
	    "The reliable channel to the neighbor."
	::= {ndNbrEntry 2 }

ndNbrState				OBJECT-TYPE
	SYNTAX	INTEGER {
		    unknown	(1),
		    existent	(2),
		    up		(3),
		    comingdown  (4)
		}
	ACCESS	read-only
	STATUS	mandatory
	DESCRIPTION
	    "The neighbor's state."
	::= {ndNbrEntry 3 }

--
-- 
-- ND Switch Up/Down Variables
-- 

ndSwudGroup 		OBJECT IDENTIFIER ::= { lsND 4 }

ndSwudTable				OBJECT-TYPE
	SYNTAX	SEQUENCE OF NdSwudEntry
	ACCESS	not-accessible
	STATUS	mandatory
	DESCRIPTION
	    "A table containing switch up/down protocol parameters
		for each switch slot."
	::= { ndSwudGroup 1 }

ndSwudEntry				OBJECT-TYPE
	SYNTAX	NdSwudEntry
	ACCESS	not-accessible
	STATUS	mandatory
	DESCRIPTION
	    "The switch up/down protocol parameters for a single switch
		slot."
	INDEX	{ ndSwudIndex }
	::= { ndSwudTable 1 }

NdSwudEntry ::=
	SEQUENCE {
	    ndSwudIndex				INTEGER,
	    ndOperIntvl				INTEGER,
	    ndOperJ				INTEGER,
	    ndOperK				INTEGER,
	    ndOperM				INTEGER,
	    ndOperN				INTEGER,
	    ndAdminIntvl			INTEGER,
	    ndAdminJ				INTEGER,
	    ndAdminK				INTEGER,
	    ndAdminM				INTEGER,
	    ndAdminN				INTEGER,
	    ndTrigger				INTEGER
	}

ndSwudIndex				OBJECT-TYPE
	SYNTAX	INTEGER
	ACCESS	read-only
	STATUS	mandatory
	DESCRIPTION
	    "The switch slot to which the parameters correspond."
	::= { ndSwudEntry 1 }


ndOperIntvl				OBJECT-TYPE
	SYNTAX	INTEGER
	ACCESS	read-only
	STATUS	mandatory
	DESCRIPTION
	    "The operational interval between switch up/down messages
		sent by ND to this slot, in units of 100 milliseconds."
	::= { ndSwudEntry 2 }

ndOperJ					OBJECT-TYPE
	SYNTAX	INTEGER
	ACCESS	read-only
	STATUS	mandatory
	DESCRIPTION
	    "The operational J parameter for this slot."
	::= { ndSwudEntry 3 }

ndOperK					OBJECT-TYPE
	SYNTAX	INTEGER
	ACCESS	read-only
	STATUS	mandatory
	DESCRIPTION
	    "The operational K parameter for this slot."
	::= { ndSwudEntry 4 }

ndOperM					OBJECT-TYPE
	SYNTAX	INTEGER
	ACCESS	read-only
	STATUS	mandatory
	DESCRIPTION
	    "The operational M parameter for this slot."
	::= { ndSwudEntry 5 }

ndOperN					OBJECT-TYPE
	SYNTAX	INTEGER
	ACCESS	read-only
	STATUS	mandatory
	DESCRIPTION
	    "The operational N parameter for this slot."
	::= { ndSwudEntry 6 }

ndAdminIntvl				OBJECT-TYPE
	SYNTAX	INTEGER
	ACCESS	read-write
	STATUS	mandatory
	DESCRIPTION
	    "The administratively desired interval between switch
		up/down messages sent by ND to this slot, in units
		of 100 milliseconds."
	DEFVAL { 3 } -- Send switch up/down messages every 300 milliseconds
	::= { ndSwudEntry 7 }

ndAdminJ				OBJECT-TYPE
	SYNTAX	INTEGER
	ACCESS	read-write
	STATUS	mandatory
	DESCRIPTION
	    "The administratively desired J parameter for this slot."
	DEFVAL { 1 } -- Receive j/m messages to bring line up
	::= { ndSwudEntry 8 }

ndAdminK				OBJECT-TYPE
	SYNTAX	INTEGER
	ACCESS	read-write
	STATUS	mandatory
	DESCRIPTION
	    "The administratively desired K parameter for this slot."
	DEFVAL { 1 } -- Receive k/n messages to keep line up
	::= { ndSwudEntry 9 }

ndAdminM				OBJECT-TYPE
	SYNTAX	INTEGER
	ACCESS	read-write
	STATUS	mandatory
	DESCRIPTION
	    "The administratively desired M parameter for this slot."
	DEFVAL { 1 } -- Receive j/m messages to bring line up
	::= { ndSwudEntry 10 }

ndAdminN				OBJECT-TYPE
	SYNTAX	INTEGER
	ACCESS	read-write
	STATUS	mandatory
	DESCRIPTION
	    "The administratively desired N parameter for this slot."
	DEFVAL { 1 } -- Receive k/n messages to keep line up
	::= { ndSwudEntry 11 }

ndTrigger				OBJECT-TYPE
	SYNTAX	INTEGER
	ACCESS	read-write
	STATUS	mandatory
	DESCRIPTION
	    "Transfer administratively desired to operational parameters."
	::= { ndSwudEntry 12 }


ndSwudStatsInputErrors				OBJECT-TYPE
	SYNTAX	Counter
	ACCESS	read-only
	STATUS	mandatory
	DESCRIPTION
	    "The number of errors received on switch up/down input cells."
	::= { ndSwudGroup 2 }

ndSwudStatsTable			OBJECT-TYPE
	SYNTAX	SEQUENCE OF NdSwudStatsEntry
	ACCESS	not-accessible
	STATUS	mandatory
	DESCRIPTION
	    "A table containing switch up/down protocol statistics
		for each switch slot."
	::= { ndSwudGroup 3 }

ndSwudStatsEntry			OBJECT-TYPE
	SYNTAX	NdSwudStatsEntry
	ACCESS	not-accessible
	STATUS	mandatory
	DESCRIPTION
	    "Switch up/down protocol statistics for a single switch
		slot."
	INDEX	{ ndSwudStatsIndex }
	::= { ndSwudStatsTable 1 }

NdSwudStatsEntry ::=
	SEQUENCE {
	    ndSwudStatsIndex			INTEGER,
	    ndInputCells			Counter,
	    ndInputErrs		        	Counter,
	    ndOutputCells			Counter,
	    ndOutputErrs			Counter
	}

ndSwudStatsIndex			OBJECT-TYPE
	SYNTAX	INTEGER
	ACCESS	read-only
	STATUS	mandatory
	DESCRIPTION
	    "The switch slot to which the statistics correspond."
	::= { ndSwudStatsEntry 1 }


ndInputCells				OBJECT-TYPE
	SYNTAX	Counter
	ACCESS	read-only
	STATUS	mandatory
	DESCRIPTION
	    "The number of switch up/down cells received from this
		switch slot."
	::= { ndSwudStatsEntry 2 }

ndInputErrs				OBJECT-TYPE
	SYNTAX	Counter
	ACCESS	read-only
	STATUS	mandatory
	DESCRIPTION
	    "The number of errored switch up/down cells received from this
		switch slot."
	::= { ndSwudStatsEntry 3 }

ndOutputCells				OBJECT-TYPE
	SYNTAX	Counter
	ACCESS	read-only
	STATUS	mandatory
	DESCRIPTION
	    "The number of switch up/down cells sent to this
		switch slot."
	::= { ndSwudStatsEntry 4 }

ndOutputErrs				OBJECT-TYPE
	SYNTAX	Counter
	ACCESS	read-only
	STATUS	mandatory
	DESCRIPTION
	    "The number of errors reported on switch up/down cells
		sent to this switch slot."
	::= { ndSwudStatsEntry 5 }


--
--
-- ND Client Variables
-- 

ndClientGroup 		OBJECT IDENTIFIER ::= { lsND 5 }

ndClientCount				OBJECT-TYPE
	SYNTAX	Counter
	ACCESS	read-only
	STATUS	mandatory
	DESCRIPTION
	    "The number of registered ND client processes."
	::= { ndClientGroup 1 }

ndClientTable				OBJECT-TYPE
	SYNTAX	SEQUENCE OF NdClientEntry
	ACCESS	not-accessible
	STATUS	mandatory
	DESCRIPTION
	    "A table containing information about each ND client process."
	::= { ndClientGroup 2 }

ndClientEntry				OBJECT-TYPE
	SYNTAX	NdClientEntry
	ACCESS	not-accessible
	STATUS	mandatory
	DESCRIPTION
	    "The information regarding a single ND client process."
	INDEX	{ ndClientID }
	::= { ndClientTable 1 }

NdClientEntry ::=
	SEQUENCE {
	    ndClientID				INTEGER,
	    ndClientType			INTEGER,
	    ndClientSubType			INTEGER,
	    ndClientEIA				INTEGER,
	    ndClientRegistration		INTEGER
	}

ndClientID				OBJECT-TYPE
	SYNTAX	INTEGER
	ACCESS	read-only
	STATUS	mandatory
	DESCRIPTION
	    "The ND client process identifier."
	::= { ndClientEntry 1 }

ndClientType				OBJECT-TYPE
	SYNTAX	INTEGER {
		    nd		(3),
		    gid		(4),
		    lcc		(5),
		    ca		(6),
		    sys		(7)
		}
	ACCESS	read-only
	STATUS	mandatory
	DESCRIPTION
	    "The ND client type."
	::= { ndClientEntry 2 }

ndClientSubType				OBJECT-TYPE
	SYNTAX	INTEGER
	ACCESS	read-only
	STATUS	mandatory
	DESCRIPTION
	    "The ND client subtype, if applicable.
	     
	     Certain processes with the same major type, e.g. sys,
	     are distinguished by differing subtypes." 
	::= { ndClientEntry 3 }

ndClientEIA				OBJECT-TYPE
	SYNTAX	INTEGER
	ACCESS	read-only
	STATUS	mandatory
	DESCRIPTION
	    "The internal card address associated with the
		ND client process, if applicable.

		Edge and trunk card control processes are associated
		with a unique card address.  The NP card control process
		and the Congestion Avoidance information distribution
		process share the internal card address of the local
		NP."
	::= { ndClientEntry 4 }


ndClientRegistration				OBJECT-TYPE
	SYNTAX	INTEGER
	ACCESS	read-only
	STATUS	mandatory
	DESCRIPTION
	    "A mask of events for which the ND client is registered."
	::= { ndClientEntry 5 }


--
-- 
-- ND Internal Variables
-- 

ndInternalGroup		OBJECT IDENTIFIER ::= { lsND 6 }

ndInternalDebugLevel			OBJECT-TYPE
	SYNTAX	INTEGER
	ACCESS	read-write
	STATUS	mandatory
	DESCRIPTION
	    "ND internal debugging variable."
	DEFVAL { 0 } -- No debugging level
	::= { ndInternalGroup 1 }

ndInternalDebugFlags			OBJECT-TYPE
	SYNTAX	INTEGER 
	ACCESS	read-write
	STATUS	mandatory
	DESCRIPTION
	    "ND internal debugging variable."
	DEFVAL { 0 } -- No debugging flags
	::= { ndInternalGroup 2 }

--
-- 
-- ND Redundancy Variables
-- 

ndRedundancyGroup		OBJECT IDENTIFIER ::= { lsND 7 }

ndPrimaryNP			OBJECT-TYPE
	SYNTAX	INTEGER
	ACCESS	read-only
	STATUS	mandatory
	DESCRIPTION
	    "Slot number of primary NP."
	DEFVAL { 0 } -- No primary NP
	::= { ndRedundancyGroup 1 }

ndThisNP			OBJECT-TYPE
	SYNTAX	INTEGER 
	ACCESS	read-only
	STATUS	mandatory
	DESCRIPTION
	    "Slot number of currently connected NP."
	::= { ndRedundancyGroup 2 }

ndForceToBackup			OBJECT-TYPE
	SYNTAX	INTEGER 
	ACCESS	read-write
	STATUS	mandatory
	DESCRIPTION
	    "Force this NP to become backup."
	::= { ndRedundancyGroup 3 }

--
-- 
-- LWMA objects
-- 

         lwmaInfo           OBJECT IDENTIFIER ::= { atmSwitch 18 }

         lwmaTable OBJECT-TYPE
    	    SYNTAX  SEQUENCE OF LwmaEntry
            ACCESS  not-accessible
	    STATUS  mandatory
	    DESCRIPTION
                "Table of perprocess LWMA private info"
	    ::= { lwmaInfo 1 }

	 lwmaEntry OBJECT-TYPE
	    SYNTAX   LwmaEntry
	    ACCESS   not-accessible
	    STATUS   mandatory
	    DESCRIPTION
	        "An entry in the LWMA table."
	    INDEX   { lwmaIndex }
	    ::= { lwmaTable 1 }

	 LwmaEntry ::=
	    SEQUENCE {
	        lwmaIndex
	        	INTEGER,
    	    	lwmaCreationTime
    	    	    	INTEGER,
    	    	lwmaTableNotification
    	    	    	OBJECT IDENTIFIER,
    	    	lwmaTrapLevel
    	    	    	INTEGER,
    	        lwmaTrapNumber
    	    	    	INTEGER,
    	    	lwmaTrapOnOffState
    	    	    	INTEGER,
    	    	lwmaTrapCliAlias
    	    	    	OCTET STRING (SIZE(32))
	        }
    	        	    
         lwmaIndex OBJECT-TYPE
              SYNTAX  INTEGER
    	      ACCESS  read-only
              STATUS  mandatory
              DESCRIPTION
                  "Unique Index consisting of LWMA number."
          ::= { lwmaEntry 1 }

         lwmaCreationTime OBJECT-TYPE
              SYNTAX  INTEGER
    	      ACCESS  read-only
              STATUS  mandatory
              DESCRIPTION
                  "Unix time in seconds marking start of MMA."
          ::= { lwmaEntry 2 }

         lwmaTableNotification OBJECT-TYPE
              SYNTAX  OBJECT IDENTIFIER
    	      ACCESS  read-only
              STATUS  mandatory
              DESCRIPTION
                  "Object-ID of last table completing configuration"
          ::= { lwmaEntry 3 }

         lwmaTrapLevel OBJECT-TYPE
    	    	SYNTAX INTEGER {
    	    	    	operational (1),
    	    	    	informational (2),
    	    	    	trace  (3),
    	    	    	debug  (4)
        	    	}
    	      ACCESS  read-write
              STATUS  mandatory
              DESCRIPTION
                  "Trap filter level for the lwma."
          ::= { lwmaEntry 4 }

       	lwmaTrapNumber OBJECT-TYPE
    	    	SYNTAX INTEGER
    	    	ACCESS read-write
    	    	STATUS mandatory
    	    	DESCRIPTION
    	    	    "Trap Number used by the state and action variables"
    	    	::= { lwmaEntry 5 }

    	lwmaTrapOnOffState OBJECT-TYPE
    	    	SYNTAX INTEGER {
    	    	    	trapOn (1),
    	    	    	trapOff(2)
    	    	    	}
    	    	ACCESS read-write
    	    	STATUS mandatory
    	    	DESCRIPTION
    	    	    "On/Off State of Trap specified in lwmaTrapNumber"
    	    	::= { lwmaEntry 6}

    	lwmaTrapCliAlias OBJECT-TYPE
    	    	SYNTAX OCTET STRING (SIZE(32))
    	    	ACCESS read-only
    	    	STATUS mandatory
    	    	DESCRIPTION
    	    	    "Name for this process that can be used in the
    	    	     CLI trap interface."
    	    	::= { lwmaEntry 7 }

--
--
--

-- This section is reserved for internet extension subtrees.

	lightStreamBridge     OBJECT IDENTIFIER ::= { lightStreamInternet 1 }



-- Bridge extensions

	  lightStreamBridgePortTable OBJECT-TYPE
	      SYNTAX  SEQUENCE OF LightStreamBridgePortEntry
	      ACCESS  not-accessible
	      STATUS  mandatory
	      DESCRIPTION
	              "Proprietary port parameters needed for
		      LightStream node configuration.  This table
		      contains one entry for each bridge port."
	      ::= { lightStreamBridge 1 }

	  lightStreamBridgePortEntry OBJECT-TYPE
	      SYNTAX  LightStreamBridgePortEntry
              ACCESS  not-accessible
              STATUS  mandatory
              DESCRIPTION
                      "Objects required for a given bridge port."
              INDEX    { lightStreamBrPortPort }
              ::= { lightStreamBridgePortTable 1 }

          LightStreamBridgePortEntry ::=
	        SEQUENCE {
		    lightStreamBrPortPort
		    	INTEGER,
		    lightStreamBrPortDefaultAction
		    	LightStreamFilterAction,
		    lightStreamBrPortBcastRateLimit
		    	INTEGER,
		    lightStreamBrPortDroppedBcastPkts
		    	Counter
		}



          lightStreamBrPortPort OBJECT-TYPE
              SYNTAX  INTEGER
              ACCESS  read-only
              STATUS  mandatory
              DESCRIPTION
                      "The value of the instance of the dot1dBasePort
		      object, defined in the standard Bridge MIB
		      (RFC1286), for the port this entry corresponds to."
              ::= { lightStreamBridgePortEntry 1 }

          lightStreamBrPortDefaultAction OBJECT-TYPE
              SYNTAX  LightStreamFilterAction
              ACCESS  read-write
              STATUS  mandatory
              DESCRIPTION
                      "This is the action taken on frames received
		      that do not match a defined filter."
              DEFVAL   { forward }
              ::= { lightStreamBridgePortEntry 2 }


          lightStreamBrPortBcastRateLimit OBJECT-TYPE
              SYNTAX  INTEGER (-1..127)
              ACCESS  read-write
              STATUS  mandatory
              DESCRIPTION
                      "Number of broadcast packets that this node
		      forwards per second.  The node discards all
		      additional packets per second.

		      If the value is zero, all broadcast packets are
		      discarded.

		      If the value is -1 all broadcast packets
		      are forwarded.  That is, there is no limit on
		      broadcasts."
              DEFVAL   { -1 }
              ::= { lightStreamBridgePortEntry 3 }


          lightStreamBrPortDroppedBcastPkts OBJECT-TYPE
              SYNTAX  Counter
              ACCESS  read-only
              STATUS  mandatory
              DESCRIPTION
                      "The number of broadcast packets dropped because
		      the lightStreamBrPortBcastRateLimit was exceeded."
              ::= { lightStreamBridgePortEntry 4 }


--
--
--

          lightStreamBridgeFilterTable OBJECT-TYPE
              SYNTAX  SEQUENCE OF LightStreamBridgeFilterEntry
              ACCESS  not-accessible
              STATUS  mandatory
              DESCRIPTION
                      "A list of filters.  Reverse Polish Notation
		      (RPN) is being used here to provide the most
		      flexibility in defining more complex filters in
		      the future. 

		      Each filter is represented by a list of entries.
		      Each entry is a single RPN token.  To create an
		      entry, create the list of tokens as follows:

			     More than one token can be contained
				  in a single message.
			     All fields of a single token must be
				 in the same message.
			     The lightStreamBrFilterStatus object of
				 all intermediate tokens must contain
				 the value 'intermediateToken'.
			     The lightStreamBrFilterStatus object of
				 the last token must contain the value
				 'complete'.
			When the last token is created with a status
			of 'complete' the status field of every prior
			token associated with that filter is set to
			'complete'. 

			When the filter is set to 'complete', it is
			available for use in a 
			lightStreamBridgeFilterParameterEntry.  The
			filter is not actually used until its ID is
			placed in a
			lightStreamBridgeFilterParameterEntry and the
			associated parameters are defined. 

			A filter may be used more than once in the
			lightStreamBridgeFilterParameterTable.  The
			agent does not permit the user to 'delete' the
			filter entry until it is removed from the
			lightStreamBridgeFilterParameterTable.  

			When a filter is placed into or removed from
			the lightStreamBridgeFilterParameterTable,
			its new state becomes active immediately.

			The agent provides timeout service for
			partially constructed filters.  If a manager
			doesn't complete a filter definition within the
			timeout period (currently 3 minutes), the
			agent removes all tokens associated with that
			filter." 
              ::= { lightStreamBridge 2 }


          lightStreamBridgeFilterEntry OBJECT-TYPE
              SYNTAX  LightStreamBridgeFilterEntry
              ACCESS  not-accessible
              STATUS  mandatory
              DESCRIPTION
                      "A single filter consists of multiple
		      lightStreamBridgeFilterEntries.  Each entry
		      represents a single token of a given filter."
              INDEX    { lightStreamBrFilterId,
			 lightStreamBrFilterTokenIndex }
              ::= { lightStreamBridgeFilterTable 1 }

          LightStreamBridgeFilterEntry ::=
	        SEQUENCE {
		    lightStreamBrFilterId
		    	INTEGER,
		    lightStreamBrFilterTokenIndex
		    	INTEGER,
		    lightStreamBrFilterTokenType
		    	INTEGER,
		    lightStreamBrFilterTokenValue
		    	DisplayString,
		    lightStreamBrFilterStatus
		    	INTEGER
		}


          lightStreamBrFilterId OBJECT-TYPE
              SYNTAX  INTEGER (1..65535)
              ACCESS  read-only
              STATUS  mandatory
              DESCRIPTION
                      "The ID assigned to this filter."
              ::= { lightStreamBridgeFilterEntry 1 }


          lightStreamBrFilterTokenIndex OBJECT-TYPE
              SYNTAX  INTEGER
              ACCESS  read-only
              STATUS  mandatory
              DESCRIPTION
                      "The RPN index of this token within the
		      filter.

		      This value must be assigned sequentially
		      starting with 1."
              ::= { lightStreamBridgeFilterEntry 2 }


          lightStreamBrFilterTokenType OBJECT-TYPE
              SYNTAX  INTEGER {
			      operation(1),
			      frameField(2),
			      macAddrType(3),
			      etherType(4),
			      llcSAPType(5),
			      reserved(6),
			      snapOuiType(7)
			      }
              ACCESS  read-write
              STATUS  mandatory
              DESCRIPTION
                      "This defines the type of token contained in
		      this entry.

		      There is no default value for this object, its
		      value must be contained in the creation message."
              ::= { lightStreamBridgeFilterEntry 3 }


          lightStreamBrFilterTokenValue OBJECT-TYPE
              SYNTAX  DisplayString
              ACCESS  read-write
              STATUS  mandatory
              DESCRIPTION
                      "The value for this token.  The appropriate
		      value depends on the
		      lightStreamBrFilterTokenType.  Because instances
		      of this object can be of diverse types, they are
		      exchanged as DisplayStrings and the agent parses
		      it according to the type.  

		      If the type is 'operation', the agent expects
		      one of the following character strings:
				maskAnd
		      		and
				or
				equal
				notEqual
				greater
				greaterOrEqual
				less
				lessOrEqual

		      If the type is 'macAddrType' the agent expects
		      a MAC address DisplayString in the format
		      xx:xx:xx:xx:xx:xx.

		      If the type is 'frameField' the agent will
		      expect of one of the following character strings:
			     macSrc
			     macDst
			     macProto
			     llcSSAP
			     llcDSAP
			     snapOUI
			     snapProto

		      For all other types, the agent expects a
		      hex digit displayString in the form 0x800.

		      This object has no default value.  It must be
		      explicitly set in the creation message."
              ::= { lightStreamBridgeFilterEntry 4 }


          lightStreamBrFilterStatus OBJECT-TYPE
              SYNTAX  INTEGER {
			      complete(1),
			      delete(2),
			      intermediateToken(4)
			      }			      
              ACCESS  read-write
              STATUS  mandatory
              DESCRIPTION
                      "To define an interim token, set this field to
		      'intermediateToken'. 

		      To define the final token set this field to
		      'complete'.  This has the side-effect of
		      setting the lightStreamBrFilterStatus fields of all
		      tokens for this filter to 'complete'.

		      To delete an unassigned filter, set this value to
		      'delete' in any of the filter's token entries.
		      This has the side-effect of setting the
		      lightStreamBrFilterStatus fields of all tokens
		      for this filter to 'delete'.

		      This object does not have a default value.  To
		      create an entry this object must be explicitly
		      contained in the set message." 
              ::= { lightStreamBridgeFilterEntry 5 }


--
--
--

          lightStreamBridgeFilterParameterTable OBJECT-TYPE
              SYNTAX  SEQUENCE OF LightStreamBridgeFilterParameterEntry
              ACCESS  not-accessible
              STATUS  mandatory
              DESCRIPTION
                      "This table contains the list of assigned
		      filters and the parameters associated
		      with it.

		      To add an entry to this table, all non-defaulted
		      objects must be contained in a single message
		      and the lightStreamBrFilterParmFilterId must
		      already be created in the
		      lightStreamBridgeFilterTable."		      
              ::= { lightStreamBridge 3 }


          lightStreamBridgeFilterParameterEntry OBJECT-TYPE
              SYNTAX  LightStreamBridgeFilterParameterEntry
              ACCESS  not-accessible
              STATUS  mandatory
              DESCRIPTION
                      "The objects associated with a single assigned
		      filter."
              INDEX    { lightStreamBrFilterParmPort,
			 lightStreamBrFilterParmFilterId }
              ::= { lightStreamBridgeFilterParameterTable 1 }

          LightStreamBridgeFilterParameterEntry ::=
	        SEQUENCE {
		    lightStreamBrFilterParmPort
		    	INTEGER,
		    lightStreamBrFilterParmFilterId
		    	INTEGER,
		    lightStreamBrFilterParmFilterPriority
		    	INTEGER,
		    lightStreamBrFilterParmAction
		    	LightStreamFilterAction,
		    lightStreamBrFilterParmMatchCounts
		    	Counter,
		    lightStreamBrFilterParmValidation
		    	LightStreamValidation
		}



          lightStreamBrFilterParmPort OBJECT-TYPE
              SYNTAX  INTEGER
              ACCESS  read-only
              STATUS  mandatory
              DESCRIPTION
                      "The dot1dBasePort, defined in the standard
		      Bridge MIB (RFC1286), this entry is defined
		      for." 
              ::= { lightStreamBridgeFilterParameterEntry 1 }


          lightStreamBrFilterParmFilterId OBJECT-TYPE
              SYNTAX  INTEGER
              ACCESS  read-only
              STATUS  mandatory
              DESCRIPTION
                      "The lightStreamBrFilterId being assigned here."
              ::= { lightStreamBridgeFilterParameterEntry 2 }


          lightStreamBrFilterParmFilterPriority OBJECT-TYPE
              SYNTAX  INTEGER
              ACCESS  read-write
              STATUS  mandatory
              DESCRIPTION
                      "The precedence assigned to this filter.  The
		      value 1 gives the object the highest priority on
		      this port. 

		      It is recommended that these not be assigned
		      sequentially.  Sequential numbering would make it
		      difficult to re-prioritize the filters."
              ::= { lightStreamBridgeFilterParameterEntry 3 }


          lightStreamBrFilterParmAction OBJECT-TYPE
              SYNTAX  LightStreamFilterAction
              ACCESS  read-write
              STATUS  mandatory
              DESCRIPTION
                      "Definition of what action should be taken when a
		      packet matching this filter is encountered."
              ::= { lightStreamBridgeFilterParameterEntry 4 }


          lightStreamBrFilterParmMatchCounts OBJECT-TYPE
              SYNTAX  Counter
              ACCESS  read-only
              STATUS  mandatory
              DESCRIPTION
                      "The number of times this filter instance was
		      matched." 
              ::= { lightStreamBridgeFilterParameterEntry 5 }

          lightStreamBrFilterParmValidation OBJECT-TYPE
              SYNTAX  LightStreamValidation
              ACCESS  read-write
              STATUS  mandatory
              DESCRIPTION
                      "This object indicates whether the user has
		      validated or invalidated this entry.
		      
		      This entry does not have a default value.  To
		      create an entry this object must be explicitly
		      contained in the set message."
              ::= { lightStreamBridgeFilterParameterEntry 6 }



          lightStreamBrStaticGoToCardSize OBJECT-TYPE
              SYNTAX  INTEGER
              ACCESS  read-only
              STATUS  mandatory
              DESCRIPTION
                      "This object indicates how many bytes of the bit
		      string dot1dStaticGoTo represent a single
		      card.  There must be enough bytes to represent
		      all the ports on a card, and this is release
		      specific.  The dot1dStaticGoTo object is a bit
		      string that represents the bridging ports on the
		      LightStream Node."
              ::= { lightStreamBridge 4 }


--
--
--

-- This section reserved for VLI definitions



          lightStreamVliVersion OBJECT-TYPE
              SYNTAX  INTEGER {
			      version-1(1)
			      }
              ACCESS  read-only
              STATUS  mandatory
              DESCRIPTION
                      "The version of VLI implemented in this node."
              ::= { lightStreamVli 1 }

          lightStreamVliPortCtlTable OBJECT-TYPE
              SYNTAX  SEQUENCE OF LightStreamVliPortCtlEntry
              ACCESS  not-accessible
              STATUS  mandatory
              DESCRIPTION
                      "This table contains the control information for
		      port based VLI."
              ::= { lightStreamVli 4 }


          lightStreamVliPortCtlEntry OBJECT-TYPE
              SYNTAX  LightStreamVliPortCtlEntry
              ACCESS  not-accessible
              STATUS  mandatory
              DESCRIPTION
                      "Information needed to manage port based VLI on
		      a given bridge port."
              INDEX    { lightStreamVliPortCtlPort }
              ::= { lightStreamVliPortCtlTable 1 }

          LightStreamVliPortCtlEntry ::=
	        SEQUENCE {
		    lightStreamVliPortCtlPort
		    	INTEGER,
		    lightStreamVliPortCtlMode
		    	INTEGER
		}


          lightStreamVliPortCtlPort OBJECT-TYPE
              SYNTAX  INTEGER
              ACCESS  read-only
              STATUS  mandatory
              DESCRIPTION
                      "The bridge port this entry corresponds to.
		      This value is the same as dot1dBasePort which is
		      defined in the IETF standard Bridge MIB."
              ::= { lightStreamVliPortCtlEntry 1 }


          lightStreamVliPortCtlMode OBJECT-TYPE
              SYNTAX  INTEGER {
			      include(1),
			      exclude(2)
			      }
              ACCESS  read-write
              STATUS  mandatory
              DESCRIPTION
                      "This defines the type of control to be
		      instrumented on this port.

		      include:  When this object is set to include,
				port based VLI will process only
				the work groups defined in the
				corresponding work group table
				entries.  All other work groups will 
				be filtered out on this port.

		      exclude:  When this object is set to exclude,
				port based VLI will process all work
				groups except those listed in the
				corresponding work group table
				entries.  Those listed in the
				lightStreamVliPortWorkGroupTable will
				be filtered.

		      The default state of exclude with an empty work
		      group table allows all work groups to be
		      recognized as valid on this port."
              DEFVAL   { 1 }
              ::= { lightStreamVliPortCtlEntry 2 }



--
--
--


          lightStreamVliPortWorkGroupTable OBJECT-TYPE
              SYNTAX  SEQUENCE OF LightStreamVliPortWorkGroupEntry
              ACCESS  not-accessible
              STATUS  mandatory
              DESCRIPTION
                      "The list of work groups defined for port based
		      VLI management."
              ::= { lightStreamVli 5 }


          lightStreamVliPortWorkGroupEntry OBJECT-TYPE
              SYNTAX  LightStreamVliPortWorkGroupEntry
              ACCESS  not-accessible
              STATUS  mandatory
              DESCRIPTION
                      "A work group to port association."
              INDEX    { lightStreamVliPortWorkGroupPort,
			 lightStreamVliPortWorkGroupID }
              ::= { lightStreamVliPortWorkGroupTable 1 }

          LightStreamVliPortWorkGroupEntry ::=
	        SEQUENCE {
		    lightStreamVliPortWorkGroupPort
		    	INTEGER,
		    lightStreamVliPortWorkGroupID
		    	INTEGER (1..65535),
		    lightStreamVliPortWorkGroupValidation
		    	LightStreamValidation
		}


          lightStreamVliPortWorkGroupPort OBJECT-TYPE
              SYNTAX  INTEGER
              ACCESS  read-only
              STATUS  mandatory
              DESCRIPTION
                      "The port this work group is being defined on.
		      This value is the same as dot1dBasePort."
              ::= { lightStreamVliPortWorkGroupEntry 1 }


          lightStreamVliPortWorkGroupID OBJECT-TYPE
              SYNTAX  INTEGER (1..65535)
              ACCESS  read-only
              STATUS  mandatory
              DESCRIPTION
                      "The identifier of the work group being assigned
		      to this port.  This must have a corresponding
		      entry in the lightStreamVliWorkGroupTable." 
              ::= { lightStreamVliPortWorkGroupEntry 2 }


          lightStreamVliPortWorkGroupValidation OBJECT-TYPE
              SYNTAX  LightStreamValidation
              ACCESS  read-write
              STATUS  mandatory
              DESCRIPTION
		      "For conceptual row addition, this table
		      requires all non-defaulted objects for a given
		      entry to be contained in a single SNMP message.

		      This object will not default.  To create a new
		      entry, this object must be explicitly set to
		      valid.  To remove an entry, this object must be
		      explicitly set to invalid."
              ::= { lightStreamVliPortWorkGroupEntry 3 }

--
--
--

-- To simplify get-next processing for our proprietary applications,
-- this object is being placed here as an "end of MIB" marker.


          lightStreamEndOfMib OBJECT-TYPE
              SYNTAX  INTEGER
              ACCESS  read-only
              STATUS  mandatory
              DESCRIPTION
		      "Always returns 1."
              ::= { lightStreamEOM 1 }


    END
