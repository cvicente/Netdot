BAY-STACK-NOTIFY-CONTROL-MIB DEFINITIONS ::= BEGIN

IMPORTS
    OBJECT-TYPE, MODULE-IDENTITY
        FROM SNMPv2-SMI
    TruthValue, RowStatus
        FROM SNMPv2-TC
    bayStackMibs
        FROM SYNOPTICS-ROOT-MIB;

bayStackNotifyControlMib MODULE-IDENTITY
    LAST-UPDATED    "200810170000Z"
    ORGANIZATION    "Nortel Networks"
    CONTACT-INFO    "Nortel Networks"
    DESCRIPTION
        "Nortel Networks Notification Control MIB

         Copyright 2008 Nortel Networks, Inc.
         All rights reserved.
         This Nortel Networks SNMP Management Information Base
         Specification embodies Nortel Networks' confidential and
         proprietary intellectual property. Nortel Networks retains
         all title and ownership in the Specification, including any
         revisions.

         This Specification is supplied 'AS IS,' and Nortel Networks
         makes no warranty, either express or implied, as to the use,
         operation, condition, or performance of the Specification."

    REVISION "200810170000Z" -- 17 October 2008
    DESCRIPTION "v1:  Initial version."

    ::= { bayStackMibs 31 }

bsncObjects OBJECT IDENTIFIER ::= { bayStackNotifyControlMib 1 }

-- -------------------------------------------------------------
-- Textual Conventions
-- -------------------------------------------------------------

-- -------------------------------------------------------------
-- Scalar Objects
-- -------------------------------------------------------------

-- -------------------------------------------------------------
-- Notification Control Table
-- -------------------------------------------------------------

bsncNotifyControlTable OBJECT-TYPE
    SYNTAX SEQUENCE OF BsncNotifyControlEntry
    MAX-ACCESS not-accessible
    STATUS current
    DESCRIPTION
        "This table is used to control generation of individual SNMP
         notification types.  The table is indexed by the OID of the
         NOTIFICATION-TYPE, and contains a flag to enable or disable
         generation of that notification type."
    ::= { bsncObjects 1 }

bsncNotifyControlEntry OBJECT-TYPE
    SYNTAX BsncNotifyControlEntry
    MAX-ACCESS not-accessible
    STATUS current
    DESCRIPTION
        "Each entry contains a flag to control generation of a specific
         notification type."
    INDEX { bsncNotifyControlType }
    ::= { bsncNotifyControlTable 1 }

BsncNotifyControlEntry ::=
    SEQUENCE {
        bsncNotifyControlType      OBJECT IDENTIFIER,
        bsncNotifyControlEnabled   TruthValue,
        bsncNotifyControlRowStatus INTEGER
    }

bsncNotifyControlType OBJECT-TYPE
    SYNTAX      OBJECT IDENTIFIER
    MAX-ACCESS  not-accessible
    STATUS      current
    DESCRIPTION
        "The OID of a NOTIFICATION-TYPE.  Note that this object cannot
         exceed a length of 114 sub-identifiers."
    ::= { bsncNotifyControlEntry 1 }
 
bsncNotifyControlEnabled OBJECT-TYPE
    SYNTAX      TruthValue
    MAX-ACCESS  read-create
    STATUS      current
    DESCRIPTION
        "Indicates whether this notification type may be generated."
    DEFVAL      { true }
    ::= { bsncNotifyControlEntry 2 }

bsncNotifyControlRowStatus OBJECT-TYPE
    SYNTAX      RowStatus
    MAX-ACCESS  read-create
    STATUS      current
    DESCRIPTION
        "Used to create/delete entries in the table.  Note that an
         implementation may simply provide permanent entries for
         every supported NOTIFICATION-TYPE."
    ::= { bsncNotifyControlEntry 3 }

END
