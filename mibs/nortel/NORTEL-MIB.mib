NORTEL-MIB DEFINITIONS ::= BEGIN
   IMPORTS 
       enterprises, MODULE-IDENTITY
	   FROM SNMPv2-SMI;

   nortel MODULE-IDENTITY
       LAST-UPDATED "200305010000Z"
       ORGANIZATION "Northern Telecom Ltd."
       CONTACT-INFO
               "   Nortel Networks
                   8200 Dixie Road
                   Brampton, Ontario L6T 5P6
                   Canada

                   1-800-4Nortel 
                   www.nortelnetworks.com"
       DESCRIPTION
               "The Nortel Networks top-level MIB definition."
       ::= { enterprises 562 } 
END
